Barracuda-LB-EXT-MIB DEFINITIONS ::=BEGIN

    IMPORTS
        MODULE-IDENTITY, OBJECT-TYPE, Counter32, Integer32, Counter64, NOTIFICATION-TYPE
          FROM SNMPv2-SMI
        TimeStamp
          FROM SNMPv2-TC
        MODULE-COMPLIANCE, OBJECT-GROUP, NOTIFICATION-GROUP 
          FROM SNMPv2-CONF
        InetAddress, InetAddressType, InetPortNumber
          FROM INET-ADDRESS-MIB
        barracuda
          FROM Barracuda-REF
        blb 
          FROM Barracuda-LB;

    blbExt MODULE-IDENTITY
        LAST-UPDATED "201308050000Z"
        ORGANIZATION "Barracuda Networks, Inc."
        CONTACT-INFO
            "
            Barracuda Networks Inc.
            3175 S. Winchester Blvd.
            Campbell, CA 95008
            "
        DESCRIPTION
            "
            Barracuda Load Balancer Extension MIB.
            
            Provides:
              Objects:
                * 1.3.6.1.4.1.20632.5.99 -- blbExt
                        * 1.3.6.1.4.1.20632.5.99.1 -- blbExtStats
                                * 1.3.6.1.4.1.20632.5.99.1.1 -- blbExtStatsSecurity
                                        * .1.3.6.1.4.1.20632.5.99.1.1.1  -- blbExtIpsReqSrvcStatsTable
                                        * .1.3.6.1.4.1.20632.5.99.1.1.2  -- blbExtIpsLrnSrvcStatsTable
                                        * .1.3.6.1.4.1.20632.5.99.1.1.3  -- blbExtIpsReqLimitStatsTable
                                        * .1.3.6.1.4.1.20632.5.99.1.1.4  -- blbExtIpsUrlNormStatsTable
                                        * .1.3.6.1.4.1.20632.5.99.1.1.5  -- blbExtIpsCookieSecStatsTable
                                        * .1.3.6.1.4.1.20632.5.99.1.1.6  -- blbExtIpsUrlAclStatsTable
                                        * .1.3.6.1.4.1.20632.5.99.1.1.7  -- blbExtIpsHdrAclStatsTable
                                        * .1.3.6.1.4.1.20632.5.99.1.1.8  -- blbExtIpsWebAddrTransStatsTable
                                        * .1.3.6.1.4.1.20632.5.99.1.1.9  -- blbExtIpsAccessCtrlStatsTable
                                        * .1.3.6.1.4.1.20632.5.99.1.1.10 -- blbExtIpsRCStatsTable
                                        * .1.3.6.1.4.1.20632.5.99.1.1.11 -- blbExtIpsUrlPolicyStatsTable
                                        * .1.3.6.1.4.1.20632.5.99.1.1.12 -- blbExtHttpProxySecStatsTable
                               * 1.3.6.1.4.1.20632.5.99.1.2 -- blbExtStatsTraffic
                                        * .1.3.6.1.4.1.20632.5.99.1.2.1  -- blbExtHttpProxyStatsTable
                                        * .1.3.6.1.4.1.20632.5.99.1.2.2  -- blbExtSslProxyStatsTable
                                        * .1.3.6.1.4.1.20632.5.99.1.2.3  -- blbExtCompressionStatsTable 
                                        * .1.3.6.1.4.1.20632.5.99.1.2.4  -- blbExtCacheStatsTable 
                                        * .1.3.6.1.4.1.20632.5.99.1.2.5  -- blbExtHttpSrvrStatsTable
                                        * .1.3.6.1.4.1.20632.5.99.1.2.6  -- blbExtSslSrvrStatsTable 
                               * 1.3.6.1.4.1.20632.5.99.1.3 -- blbExtStatsAAA
                                        * .1.3.6.1.4.1.20632.5.99.1.3.1  -- blbExtSMUserSessionTable 
                               * 1.3.6.1.4.1.20632.5.99.1.4 -- blbExtStatsSystem
                                        * 1.3.6.1.4.1.20632.5.99.1.4.1   -- blbCPUTemperature
                                        * 1.3.6.1.4.1.20632.5.99.1.4.2   -- blbSystemLoad
                                        * 1.3.6.1.4.1.20632.5.99.1.4.3   -- blbFirmwareStorage
                                        * 1.3.6.1.4.1.20632.5.99.1.4.4   -- blbMailLogStorage
                                        * 1.3.6.1.4.1.20632.5.99.1.4.5   -- blbSystemActiveServices
                                        * 1.3.6.1.4.1.20632.5.99.1.4.6   -- blbSystemOperatingServers
                                        * 1.3.6.1.4.1.20632.5.99.1.4.7   -- blbClusterStatus
                                        * 1.3.6.1.4.1.20632.5.99.1.4.8   -- blbOperationMode
                               * 1.3.6.1.4.1.20632.5.99.1.5 -- blbExtStatsGSLB
                                        * .1.3.6.1.4.1.20632.5.99.1.5.1  -- blbExtGslbStatsTable
                        * 1.3.6.1.4.1.20632.5.99.2 -- blbExtConfig
                        * 1.3.6.1.4.1.20632.5.99.3 -- blbExtTraps
                               * 1.3.6.1.4.1.20632.5.99.3.1  -- blbSystemTraps
                                        * 1.3.6.1.4.1.20632.5.99.3.1.1   -- blbCPUFanDead
                                        * 1.3.6.1.4.1.20632.5.99.3.1.2   -- blbSysFanDead
                                        * 1.3.6.1.4.1.20632.5.99.3.1.3   -- blbCPUTempHigh
                                        * 1.3.6.1.4.1.20632.5.99.3.1.4   -- blbCpuTempCritical
                                        * 1.3.6.1.4.1.20632.5.99.3.1.5   -- blbFirmwareStorageHigh
                                        * 1.3.6.1.4.1.20632.5.99.3.1.6   -- blbLogsStorageHigh
                                        * 1.3.6.1.4.1.20632.5.99.3.1.7   -- blbHighAvailabilityStatus
                                        * 1.3.6.1.4.1.20632.5.99.3.1.8   -- blbEnergizeUpdateExpire
                                        * 1.3.6.1.4.1.20632.5.99.3.1.9   -- blbFirmwareUpdateAvailable
                                        * 1.3.6.1.4.1.20632.5.99.3.1.10  -- blbAttackDefinitionUpdateAvailable
                                        * 1.3.6.1.4.1.20632.5.99.3.1.11  -- blbNewAttackDefinitionInstalled
                               * 1.3.6.1.4.1.20632.5.99.3.2  -- blbTrafficTraps
                                        * 1.3.6.1.4.1.20632.5.99.3.2.1   -- blbServiceUp
                                        * 1.3.6.1.4.1.20632.5.99.3.2.2   -- blbServiceDown
                                        * 1.3.6.1.4.1.20632.5.99.3.2.3   -- blbServerUp
                                        * 1.3.6.1.4.1.20632.5.99.3.2.4   -- blbServerDown
                                        * 1.3.6.1.4.1.20632.5.99.3.2.5   -- blbMinServerThresholdReached
                                        * 1.3.6.1.4.1.20632.5.99.3.2.6   -- blbMinServerThresholdCrossed

            "
        REVISION     "201510300000Z" -- October 30, 2015
        DESCRIPTION  "added GSLB Statistics"
        ::= { blb 99 }

blbExtStats          OBJECT IDENTIFIER ::= { blbExt 1 }
blbExtConfig         OBJECT IDENTIFIER ::= { blbExt 2 }
blbExtStatsSecurity  OBJECT IDENTIFIER ::= { blbExtStats 1 }
   --
   -- blbExtIpsReqSrvcStatsTable      .1.3.6.1.4.1.20632.5.99.1.1.1
   -- blbExtIpsLrnSrvcStatsTable      .1.3.6.1.4.1.20632.5.99.1.1.2
   -- blbExtIpsReqLimitStatsTable     .1.3.6.1.4.1.20632.5.99.1.1.3
   -- blbExtIpsUrlNormStatsTable      .1.3.6.1.4.1.20632.5.99.1.1.4
   -- blbExtIpsCookieSecStatsTable    .1.3.6.1.4.1.20632.5.99.1.1.5
   -- blbExtIpsUrlAclStatsTable       .1.3.6.1.4.1.20632.5.99.1.1.6
   -- blbExtIpsHdrAclStatsTable       .1.3.6.1.4.1.20632.5.99.1.1.7
   -- blbExtIpsWebAddrTransStatsTable .1.3.6.1.4.1.20632.5.99.1.1.8
   -- blbExtIpsAccessCtrlStatsTable   .1.3.6.1.4.1.20632.5.99.1.1.9
   -- blbExtIpsRCStatsTable           .1.3.6.1.4.1.20632.5.99.1.1.10
   -- blbExtIpsUrlPolicyStatsTable    .1.3.6.1.4.1.20632.5.99.1.1.11
   -- blbExtHttpProxySecStatsTable    .1.3.6.1.4.1.20632.5.99.1.1.12
   --
blbExtStatsTraffic   OBJECT IDENTIFIER ::= { blbExtStats 2 }
   --
   -- blbExtHttpProxyStatsTable       .1.3.6.1.4.1.20632.5.99.1.2.1
   -- blbExtSslProxyStatsTable        .1.3.6.1.4.1.20632.5.99.1.2.2
   -- blbExtCompressionStatsTable     .1.3.6.1.4.1.20632.5.99.1.2.3
   -- blbExtCacheStatsTable           .1.3.6.1.4.1.20632.5.99.1.2.4
   -- blbExtHttpSrvrStatsTable        .1.3.6.1.4.1.20632.5.99.1.2.5
   -- blbExtSslSrvrStatsTable         .1.3.6.1.4.1.20632.5.99.1.2.6
   --
blbExtStatsAAA       OBJECT IDENTIFIER ::= { blbExtStats 3 }
   --
   -- blbExtSMUserSessionTable        .1.3.6.1.4.1.20632.5.99.1.3.1
   --
blbExtStatsSystem    OBJECT IDENTIFIER ::= { blbExtStats 4 }
blbExtStatsGSLB      OBJECT IDENTIFIER ::= { blbExtStats 5 }
   --
   -- blbExtGslbStatsTable            .1.3.6.1.4.1.20632.5.99.1.5.1
   --

blbExtConfigSecurity OBJECT IDENTIFIER ::= { blbExtConfig 1 }
blbExtConfigTraffic  OBJECT IDENTIFIER ::= { blbExtConfig 2 }
blbExtConfigAAA      OBJECT IDENTIFIER ::= { blbExtConfig 3 }


blbExtHttpProxyStatsTable OBJECT-TYPE
    SYNTAX      SEQUENCE OF BlbExtHttpProxyStatsEntry
    MAX-ACCESS  not-accessible
    STATUS      current
    DESCRIPTION
        "A table of HTTP proxy stats. "
    ::= { blbExtStatsTraffic 1 }

blbExtHttpProxyStatsEntry OBJECT-TYPE
    SYNTAX     BlbExtHttpProxyStatsEntry 
    MAX-ACCESS  not-accessible
    STATUS      current
    DESCRIPTION
           "HTTP proxy stats entry. "
    INDEX {httpProxyAddressType, httpProxyAddress, httpProxyPort}
    ::= { blbExtHttpProxyStatsTable 1 }

BlbExtHttpProxyStatsEntry ::= SEQUENCE {
    httpProxyAddressType            InetAddressType,
    httpProxyAddress                InetAddress,
    httpProxyPort                   InetPortNumber,
    httpProxyActiveConn             Counter32,
    httpProxyTotalConn              Counter32,
    httpProxyTotalReq               Counter32,
    httpProxyServerReq              Counter32,   
    httpProxyServerErr              Counter32,
    httpProxyClientAbrt             Counter32,
    httpProxyServerAbrt             Counter32,
    httpProxySessionTimeOut         Counter32,
    httpProxyParseErr               Counter32,
    httpProxyUnknownRsp             Counter32,
    httpProxyInBytes                Counter64,
    httpProxyOutBytes               Counter64
} 

httpProxyAddressType  OBJECT-TYPE
    SYNTAX     InetAddressType
    MAX-ACCESS not-accessible
    STATUS     current
    DESCRIPTION
           "The type of the http Proxy address, as defined
            in the InetAddress MIB. "
    REFERENCE "RFC 4001"
    ::= { blbExtHttpProxyStatsEntry 1 }

httpProxyAddress  OBJECT-TYPE
    SYNTAX     InetAddress
    MAX-ACCESS not-accessible
    STATUS     current
    DESCRIPTION
           "The http Proxy address. "
    ::= { blbExtHttpProxyStatsEntry 2 }

httpProxyPort  OBJECT-TYPE
    SYNTAX     InetPortNumber
    MAX-ACCESS not-accessible
    STATUS     current
    DESCRIPTION
           "The port on which http Proxy is listening. "
    ::= { blbExtHttpProxyStatsEntry 3 }

httpProxyActiveConn  OBJECT-TYPE
    SYNTAX     Counter32
    MAX-ACCESS read-only
    STATUS     current
    DESCRIPTION
           "Number of active connections. "
    ::= { blbExtHttpProxyStatsEntry 4 }

httpProxyTotalConn  OBJECT-TYPE
    SYNTAX     Counter32
    MAX-ACCESS read-only
    STATUS     current
    DESCRIPTION
           "Total number of connections. "
    ::= { blbExtHttpProxyStatsEntry 5 }

httpProxyTotalReq  OBJECT-TYPE
    SYNTAX     Counter32
    MAX-ACCESS read-only
    STATUS     current
    DESCRIPTION
           "Total number of requests. "
    ::= { blbExtHttpProxyStatsEntry 6 }

httpProxyServerReq  OBJECT-TYPE
    SYNTAX     Counter32
    MAX-ACCESS read-only
    STATUS     current
    DESCRIPTION
           "Total number of server requests. "
    ::= { blbExtHttpProxyStatsEntry 7 }

httpProxyServerErr OBJECT-TYPE
    SYNTAX     Counter32
    MAX-ACCESS read-only
    STATUS     current
    DESCRIPTION
           "Total number of server errors. "
    ::= { blbExtHttpProxyStatsEntry 8 }

httpProxyClientAbrt  OBJECT-TYPE
    SYNTAX     Counter32
    MAX-ACCESS read-only
    STATUS     current
    DESCRIPTION
           "Total number of client aborts. "
    ::= { blbExtHttpProxyStatsEntry 9 }

httpProxyServerAbrt  OBJECT-TYPE
    SYNTAX     Counter32
    MAX-ACCESS read-only
    STATUS     current
    DESCRIPTION
           "Total number of server aborts. "
    ::= { blbExtHttpProxyStatsEntry 10 }

httpProxySessionTimeOut OBJECT-TYPE
    SYNTAX     Counter32
    MAX-ACCESS read-only
    STATUS     current
    DESCRIPTION
           "Total number of session timeouts. "
    ::= { blbExtHttpProxyStatsEntry 11 }

httpProxyParseErr OBJECT-TYPE
    SYNTAX     Counter32
    MAX-ACCESS read-only
    STATUS     current
    DESCRIPTION
           "Total number of parse errors. "
    ::= { blbExtHttpProxyStatsEntry 12 }

httpProxyUnknownRsp OBJECT-TYPE
    SYNTAX     Counter32
    MAX-ACCESS read-only
    STATUS     current
    DESCRIPTION
           "Total number of unknown responses. "
    ::= { blbExtHttpProxyStatsEntry 13 }

httpProxyInBytes OBJECT-TYPE
    SYNTAX     Counter64
    MAX-ACCESS read-only
    STATUS     current
    DESCRIPTION
           "Total number of In octets. "
    ::= { blbExtHttpProxyStatsEntry 14 }

httpProxyOutBytes OBJECT-TYPE
    SYNTAX     Counter64
    MAX-ACCESS read-only
    STATUS     current
    DESCRIPTION
           "Total number of Out octets. "
    ::= { blbExtHttpProxyStatsEntry 15 }

---
--blbExtSslProxyStatsTable
---

blbExtSslProxyStatsTable OBJECT-TYPE
    SYNTAX      SEQUENCE OF BlbExtSslProxyStatsEntry
    MAX-ACCESS  not-accessible
    STATUS      current
    DESCRIPTION
        "A table of SSL stats. "
    ::= { blbExtStatsTraffic 2 }

blbExtSslProxyStatsEntry OBJECT-TYPE
    SYNTAX     BlbExtSslProxyStatsEntry 
    MAX-ACCESS  not-accessible
    STATUS      current
    DESCRIPTION
           "SSL stats entry. "
    INDEX {sslProxyAddressType, sslProxyAddress, sslProxyPort}
    ::= { blbExtSslProxyStatsTable 1 }

BlbExtSslProxyStatsEntry ::= SEQUENCE {
    sslProxyAddressType           InetAddressType,
    sslProxyAddress               InetAddress,
    sslProxyPort                  InetPortNumber,
    sslProxyActiveConn            Counter32,
    sslProxyFullHandshakes        Counter32,
    sslProxyResumptionHandshakes  Counter32,
    sslProxyHandshakeAttempts     Counter32,
    sslProxyCacheHits             Counter32,
    sslProxyCacheMiss             Counter32,
    sslProxyCacheTimeouts         Counter32,
    sslProxyErrPms                Counter32,
    sslProxyAuthBadCertErr        Counter32,
    sslProxyAuthBadCNErr          Counter32,
    sslProxyBadDNCErr             Counter32,
    sslProxyBadCRLErr             Counter32,
    sslProxyInBytes               Counter64,
    sslProxyOutBytes              Counter64,
    sslProxyTotalReq              Counter32,
    sslProxyTotalConn             Counter32,
    sslProxyCurrentConn           Counter32  -- deprecated
}
 
sslProxyAddressType  OBJECT-TYPE
    SYNTAX     InetAddressType
    MAX-ACCESS not-accessible
    STATUS     current
    DESCRIPTION
           "The type of the SSL Proxy address, as defined
            in the InetAddress MIB. "
    REFERENCE "RFC 4001"
    ::= { blbExtSslProxyStatsEntry 1 }

sslProxyAddress  OBJECT-TYPE
    SYNTAX     InetAddress
    MAX-ACCESS not-accessible
    STATUS     current
    DESCRIPTION
           "The SSL Proxy address. "
    ::= { blbExtSslProxyStatsEntry 2 }

sslProxyPort  OBJECT-TYPE
    SYNTAX    InetPortNumber 
    MAX-ACCESS not-accessible
    STATUS     current
    DESCRIPTION
           "The port on which SSL Proxy is listening. "
    ::= { blbExtSslProxyStatsEntry 3 }

sslProxyActiveConn  OBJECT-TYPE
    SYNTAX     Counter32
    MAX-ACCESS read-only
    STATUS     current
    DESCRIPTION
           "Number of active connections. "
    ::= { blbExtSslProxyStatsEntry 4 }

sslProxyFullHandshakes  OBJECT-TYPE
    SYNTAX     Counter32
    MAX-ACCESS read-only
    STATUS     current
    DESCRIPTION
           "Number of full handshakes. "
    ::= { blbExtSslProxyStatsEntry 5 }

sslProxyResumptionHandshakes  OBJECT-TYPE
    SYNTAX     Counter32
    MAX-ACCESS read-only
    STATUS     current
    DESCRIPTION
           "Number of resumption handshakes. "
    ::= { blbExtSslProxyStatsEntry 6 }

sslProxyHandshakeAttempts  OBJECT-TYPE
    SYNTAX     Counter32
    MAX-ACCESS read-only
    STATUS     current
    DESCRIPTION
           "Number of handshake attempts. "
    ::= { blbExtSslProxyStatsEntry 7 }

sslProxyCacheHits  OBJECT-TYPE
    SYNTAX     Counter32
    MAX-ACCESS read-only
    STATUS     current
    DESCRIPTION
           "Number of cache hits. "
    ::= { blbExtSslProxyStatsEntry 8 }

sslProxyCacheMiss  OBJECT-TYPE
    SYNTAX     Counter32
    MAX-ACCESS read-only
    STATUS     current
    DESCRIPTION
           "Number of cache hits. "
    ::= { blbExtSslProxyStatsEntry 9 }

sslProxyCacheTimeouts  OBJECT-TYPE
    SYNTAX     Counter32
    MAX-ACCESS read-only
    STATUS     current
    DESCRIPTION
           "Number of cache hits. "
    ::= { blbExtSslProxyStatsEntry 10 }

sslProxyErrPms OBJECT-TYPE
    SYNTAX     Counter32
    MAX-ACCESS read-only
    STATUS     current
    DESCRIPTION
           "Number of PMC errors. "
    ::= { blbExtSslProxyStatsEntry 11 }

sslProxyAuthBadCertErr OBJECT-TYPE
    SYNTAX     Counter32
    MAX-ACCESS read-only
    STATUS     current
    DESCRIPTION
           "Number of bad certificates. "
    ::= { blbExtSslProxyStatsEntry 12 }

sslProxyAuthBadCNErr OBJECT-TYPE
    SYNTAX     Counter32
    MAX-ACCESS read-only
    STATUS     current
    DESCRIPTION
           "Number of bad CN errors. "
    ::= { blbExtSslProxyStatsEntry 13 }

sslProxyBadDNCErr OBJECT-TYPE
    SYNTAX     Counter32
    MAX-ACCESS read-only
    STATUS     current
    DESCRIPTION
           "Number of bad DNC errors. "
    ::= { blbExtSslProxyStatsEntry 14 }

sslProxyBadCRLErr OBJECT-TYPE
    SYNTAX     Counter32
    MAX-ACCESS read-only
    STATUS     current
    DESCRIPTION
           "Number of bad CRL errors. "
    ::= { blbExtSslProxyStatsEntry 15 }


sslProxyInBytes OBJECT-TYPE
    SYNTAX     Counter64
    MAX-ACCESS read-only
    STATUS     current
    DESCRIPTION
           "Number of IN octets. "
    ::= { blbExtSslProxyStatsEntry 16 }

sslProxyOutBytes OBJECT-TYPE
    SYNTAX     Counter64
    MAX-ACCESS read-only
    STATUS     current
    DESCRIPTION
           "Number of OUT octets. "
    ::= { blbExtSslProxyStatsEntry 17 }

sslProxyTotalReq OBJECT-TYPE
    SYNTAX     Counter32
    MAX-ACCESS read-only
    STATUS     current
    DESCRIPTION
           "Total number of requests. "
    ::= { blbExtSslProxyStatsEntry 18 }

sslProxyTotalConn OBJECT-TYPE
    SYNTAX     Counter32
    MAX-ACCESS read-only
    STATUS     current
    DESCRIPTION
           "Total number of connections. "
    ::= { blbExtSslProxyStatsEntry 19 }

sslProxyCurrentConn OBJECT-TYPE
    SYNTAX     Counter32
    MAX-ACCESS read-only
    STATUS  deprecated
    DESCRIPTION
           "Current number of connections. "
    ::= { blbExtSslProxyStatsEntry 20 }


---
--blbExtCompressionStatsTable
---

blbExtCompressionStatsTable OBJECT-TYPE
    SYNTAX      SEQUENCE OF BlbExtCompressionStatsEntry
    MAX-ACCESS  not-accessible
    STATUS      current
    DESCRIPTION
        "A table of compression stats. "
    ::= { blbExtStatsTraffic 3 }

blbExtCompressionStatsEntry OBJECT-TYPE
    SYNTAX     BlbExtCompressionStatsEntry 
    MAX-ACCESS  not-accessible
    STATUS      current
    DESCRIPTION
           "Compression stats entry. "
    INDEX {webCmprProtocol, webCmprAddressType, webCmprAddress, webCmprPort}
    ::= { blbExtCompressionStatsTable 1 }

BlbExtCompressionStatsEntry ::= SEQUENCE {
    webCmprProtocol               Integer32,
    webCmprAddressType            InetAddressType,
    webCmprAddress                InetAddress,
    webCmprPort                   InetPortNumber,
    webCmprNoOfReqCompressed      Counter32,
    webCmprCompressibleDataSize   Counter32,
    webCmprCompressedDataSize     Counter32
}

webCmprProtocol OBJECT-TYPE
    SYNTAX     Integer32 (0..65535)
    MAX-ACCESS not-accessible
    STATUS     current
    DESCRIPTION
        "The protocol used (https or https)."
    ::= { blbExtCompressionStatsEntry 1 }

webCmprAddressType OBJECT-TYPE
    SYNTAX     InetAddressType
    MAX-ACCESS not-accessible
    STATUS     current
    DESCRIPTION
           "The type of the Proxy address, as defined
            in the InetAddress MIB. "
    REFERENCE "RFC 4001"
    ::= { blbExtCompressionStatsEntry 2 }

webCmprAddress OBJECT-TYPE
    SYNTAX     InetAddress
    MAX-ACCESS not-accessible
    STATUS     current
    DESCRIPTION
           "The Proxy address. "
    ::= { blbExtCompressionStatsEntry 3 }

webCmprPort OBJECT-TYPE
    SYNTAX     InetPortNumber
    MAX-ACCESS not-accessible
    STATUS     current
    DESCRIPTION
           "The port on which Proxy is listening. "
    ::= { blbExtCompressionStatsEntry 4 }

webCmprNoOfReqCompressed OBJECT-TYPE
    SYNTAX     Counter32
    MAX-ACCESS read-only
    STATUS     current
    DESCRIPTION
           "Number of requests that got compressed. "
    ::= { blbExtCompressionStatsEntry 5 }

webCmprCompressibleDataSize OBJECT-TYPE
    SYNTAX     Counter32
    MAX-ACCESS read-only
    STATUS     current
    DESCRIPTION
           "Compressible data size. "
    ::= { blbExtCompressionStatsEntry 6 }

webCmprCompressedDataSize OBJECT-TYPE
    SYNTAX     Counter32
    MAX-ACCESS read-only
    STATUS     current
    DESCRIPTION
           "Compressed data size. "
    ::= { blbExtCompressionStatsEntry 7 }

---
--blbExtCacheStateTable
---

blbExtCacheStatsTable OBJECT-TYPE
    SYNTAX      SEQUENCE OF BlbExtCacheStatsEntry
    MAX-ACCESS  not-accessible
    STATUS      current
    DESCRIPTION
        "A table of cache stats. "
    ::= { blbExtStatsTraffic 4 }

blbExtCacheStatsEntry OBJECT-TYPE
    SYNTAX     BlbExtCacheStatsEntry 
    MAX-ACCESS  not-accessible
    STATUS      current
    DESCRIPTION
           "Cashe stats entry. "
    INDEX {webCacheProtocol, webCacheAddressType, webCacheAddress, webCachePort}
    ::= { blbExtCacheStatsTable 1 }

BlbExtCacheStatsEntry ::= SEQUENCE {
    webCacheProtocol               Integer32,
    webCacheAddressType            InetAddressType,
    webCacheAddress                InetAddress,
    webCachePort                   InetPortNumber,
    webCacheHits                   Counter32,
    webCacheMiss                   Counter32,
    webCacheStale                  Counter32,
    webCacheCacheableRes           Counter32,
    webCacheReq                    Counter32,
    webCacheCachedObjects          Counter32,
    webCacheLongHdrs               Counter32,
    webCacheBytesOut               Counter32
}
 
webCacheProtocol OBJECT-TYPE
    SYNTAX     Integer32 (0..65535)
    MAX-ACCESS not-accessible
    STATUS     current
    DESCRIPTION
        "The protocol used (https or https)."
    ::= { blbExtCacheStatsEntry 1 }

webCacheAddressType OBJECT-TYPE
    SYNTAX     InetAddressType
    MAX-ACCESS not-accessible
    STATUS     current
    DESCRIPTION
           "The type of the Proxy address, as defined
            in the InetAddress MIB. "
    REFERENCE "RFC 4001"
    ::= { blbExtCacheStatsEntry 2 }

webCacheAddress OBJECT-TYPE
    SYNTAX     InetAddress
    MAX-ACCESS not-accessible
    STATUS     current
    DESCRIPTION
           "The Proxy address. "
    ::= { blbExtCacheStatsEntry 3 }

webCachePort OBJECT-TYPE
    SYNTAX     InetPortNumber
    MAX-ACCESS not-accessible
    STATUS     current
    DESCRIPTION
           "The port on which Proxy is listening. "
    ::= { blbExtCacheStatsEntry 4 }

webCacheHits OBJECT-TYPE
    SYNTAX     Counter32
    MAX-ACCESS read-only
    STATUS     current
    DESCRIPTION
           "Number of hits. "
    ::= { blbExtCacheStatsEntry 5 }

webCacheMiss OBJECT-TYPE
    SYNTAX     Counter32
    MAX-ACCESS read-only
    STATUS     current
    DESCRIPTION
           "Number of miss. "
    ::= { blbExtCacheStatsEntry 6 }

webCacheStale OBJECT-TYPE
    SYNTAX     Counter32
    MAX-ACCESS read-only
    STATUS     current
    DESCRIPTION
           "Number of stales. "
    ::= { blbExtCacheStatsEntry 7 }

webCacheCacheableRes OBJECT-TYPE
    SYNTAX     Counter32
    MAX-ACCESS read-only
    STATUS     current
    DESCRIPTION
           "Number of cacheable responses. "
    ::= { blbExtCacheStatsEntry 8 }

webCacheReq OBJECT-TYPE
    SYNTAX     Counter32
    MAX-ACCESS read-only
    STATUS     current
    DESCRIPTION
           "Number of requests. "
    ::= { blbExtCacheStatsEntry 9 }

webCacheCachedObjects OBJECT-TYPE
    SYNTAX     Counter32
    MAX-ACCESS read-only
    STATUS     current
    DESCRIPTION
           "Number of cached objects. "
    ::= { blbExtCacheStatsEntry 10 }

webCacheLongHdrs OBJECT-TYPE
    SYNTAX     Counter32
    MAX-ACCESS read-only
    STATUS     current
    DESCRIPTION
           "Number of long headers. "
    ::= { blbExtCacheStatsEntry 11 }

webCacheBytesOut OBJECT-TYPE
    SYNTAX     Counter32
    MAX-ACCESS read-only
    STATUS     current
    DESCRIPTION
           "Number of out bytes. "
    ::= { blbExtCacheStatsEntry 12 }


---
--blbExtHttpSrvrStatsTable
---

blbExtHttpSrvrStatsTable OBJECT-TYPE
    SYNTAX      SEQUENCE OF BlbExtHttpSrvrStatsEntry
    MAX-ACCESS  not-accessible
    STATUS      current
    DESCRIPTION
        "A table of HTTP server stats. "
    ::= { blbExtStatsTraffic 5 }

blbExtHttpSrvrStatsEntry OBJECT-TYPE
    SYNTAX     BlbExtHttpSrvrStatsEntry 
    MAX-ACCESS  not-accessible
    STATUS      current
    DESCRIPTION
           "HTTP Server stats entry. "
    INDEX {httpSrvrSrvcAddressType, httpSrvrSrvcAddress, httpSrvrSrvcPort, httpSrvrAddressType, httpSrvrAddress, httpSrvrPort}
    ::= { blbExtHttpSrvrStatsTable 1 }

BlbExtHttpSrvrStatsEntry ::= SEQUENCE {
    httpSrvrSrvcAddressType        InetAddressType,
    httpSrvrSrvcAddress            InetAddress,
    httpSrvrSrvcPort               InetPortNumber,
    httpSrvrAddressType            InetAddressType,
    httpSrvrAddress                InetAddress,
    httpSrvrPort                   InetPortNumber,
    httpSrvrTotReqAccepted         Counter32,
    httpSrvrTotReqActive           Counter32,
    httpSrvrTotReqRejected         Counter32,
    httpSrvrTotSuccess             Counter32,
    httpSrvrTotRefused             Counter32,
    httpSrvrTotTimedout            Counter32,
    httpSrvrAvgReqPerConn          Counter32,
    httpSrvrTotResponse            Counter32,
    httpSrvrAvgResTime             Counter32,
    httpSrvrMaxResTime             Counter32,
    httpSrvrMinResTime             Counter32,
    httpSrvrNumReqEnqueue          Counter32,
    httpSrvrNumFreeConn            Counter32,
    httpSrvrNumOpeningConn         Counter32,
    httpSrvrNumConn                Counter32,
    httpSrvrNumIBDisabled          Counter32,
    httpSrvrNumOOBDisabled         Counter32,
    httpSrvrNumOOBEnabled          Counter32,
    httpSrvrLastDisabledTime       TimeStamp,
    httpSrvrState                  Integer32,
    httpSrvrInBytes                Counter64,
    httpSrvrOutBytes               Counter64
}

httpSrvrSrvcAddressType OBJECT-TYPE
    SYNTAX     InetAddressType
    MAX-ACCESS not-accessible
    STATUS     current
    DESCRIPTION
           "The type of the servse address, as defined
            in the InetAddress MIB. "
    REFERENCE "RFC 4001"
    ::= { blbExtHttpSrvrStatsEntry 1 }

httpSrvrSrvcAddress  OBJECT-TYPE
    SYNTAX     InetAddress
    MAX-ACCESS not-accessible
    STATUS     current
    DESCRIPTION
           "The http service address. "
    ::= { blbExtHttpSrvrStatsEntry 2 }

httpSrvrSrvcPort  OBJECT-TYPE
    SYNTAX     InetPortNumber
    MAX-ACCESS not-accessible
    STATUS     current
    DESCRIPTION
           "The port on which http service is listening. "
    ::= { blbExtHttpSrvrStatsEntry 3 }

httpSrvrAddressType  OBJECT-TYPE
    SYNTAX     InetAddressType
    MAX-ACCESS not-accessible
    STATUS     current
    DESCRIPTION
           "The type of the server address, as defined
            in the InetAddress MIB. "
    REFERENCE "RFC 4001"
    ::= { blbExtHttpSrvrStatsEntry 4 }

httpSrvrAddress  OBJECT-TYPE
    SYNTAX     InetAddress
    MAX-ACCESS not-accessible
    STATUS     current
    DESCRIPTION
           "The http server address. "
    ::= { blbExtHttpSrvrStatsEntry 5 }

httpSrvrPort  OBJECT-TYPE
    SYNTAX     InetPortNumber
    MAX-ACCESS not-accessible
    STATUS     current
    DESCRIPTION
           "The port on which http server is listening. "
    ::= { blbExtHttpSrvrStatsEntry 6 }

httpSrvrTotReqAccepted OBJECT-TYPE
    SYNTAX     Counter32
    MAX-ACCESS read-only
    STATUS     current
    DESCRIPTION
           "The total number of request accepted by http servers. "
    ::= { blbExtHttpSrvrStatsEntry 7 }

httpSrvrTotReqActive OBJECT-TYPE
    SYNTAX     Counter32
    MAX-ACCESS read-only
    STATUS     current
    DESCRIPTION
           "The total number of active request at servers. "
    ::= { blbExtHttpSrvrStatsEntry 8 }

httpSrvrTotReqRejected OBJECT-TYPE
    SYNTAX     Counter32
    MAX-ACCESS read-only
    STATUS     current
    DESCRIPTION
           "The total number of request rejected at servers. "
    ::= { blbExtHttpSrvrStatsEntry 9 }

httpSrvrTotSuccess OBJECT-TYPE
    SYNTAX     Counter32
    MAX-ACCESS read-only
    STATUS     current
    DESCRIPTION
           "The total number of request successfull at servers. "
    ::= { blbExtHttpSrvrStatsEntry 10 }

httpSrvrTotRefused OBJECT-TYPE
    SYNTAX     Counter32
    MAX-ACCESS read-only
    STATUS     current
    DESCRIPTION
           "The total number of request rejected at servers. "
    ::= { blbExtHttpSrvrStatsEntry 11 }

httpSrvrTotTimedout OBJECT-TYPE
    SYNTAX     Counter32
    MAX-ACCESS read-only
    STATUS     current
    DESCRIPTION
           "The total number of request timedout at servers. "
    ::= { blbExtHttpSrvrStatsEntry 12 }

httpSrvrAvgReqPerConn OBJECT-TYPE
    SYNTAX     Counter32
    MAX-ACCESS read-only
    STATUS     current
    DESCRIPTION
           "The average number of request per connection at servers. "
    ::= { blbExtHttpSrvrStatsEntry 13 }

httpSrvrTotResponse OBJECT-TYPE
    SYNTAX     Counter32
    MAX-ACCESS read-only
    STATUS     current
    DESCRIPTION
           "The total number of response at servers. "
    ::= { blbExtHttpSrvrStatsEntry 14 }

httpSrvrAvgResTime OBJECT-TYPE
    SYNTAX     Counter32
    MAX-ACCESS read-only
    STATUS     current
    DESCRIPTION
           "The average response time at servers. "
    ::= { blbExtHttpSrvrStatsEntry 15 }

httpSrvrMaxResTime OBJECT-TYPE
    SYNTAX     Counter32
    MAX-ACCESS read-only
    STATUS     current
    DESCRIPTION
           "The maximum response time at servers. "
    ::= { blbExtHttpSrvrStatsEntry 16 }

httpSrvrMinResTime OBJECT-TYPE
    SYNTAX     Counter32
    MAX-ACCESS read-only
    STATUS     current
    DESCRIPTION
           "The minimum response time at servers. "
    ::= { blbExtHttpSrvrStatsEntry 17 }

httpSrvrNumReqEnqueue OBJECT-TYPE
    SYNTAX     Counter32
    MAX-ACCESS read-only
    STATUS     current
    DESCRIPTION
           "The number of enqueued requests. "
    ::= { blbExtHttpSrvrStatsEntry 18 }

httpSrvrNumFreeConn OBJECT-TYPE
    SYNTAX     Counter32
    MAX-ACCESS read-only
    STATUS     current
    DESCRIPTION
           "Number of free connections. "
    ::= { blbExtHttpSrvrStatsEntry 19 }

httpSrvrNumOpeningConn OBJECT-TYPE
    SYNTAX     Counter32
    MAX-ACCESS read-only
    STATUS     current
    DESCRIPTION
           "Number of opening connection . "
    ::= { blbExtHttpSrvrStatsEntry 20 }

httpSrvrNumConn OBJECT-TYPE
    SYNTAX     Counter32
    MAX-ACCESS read-only
    STATUS     current
    DESCRIPTION
           "Number of connections . "
    ::= { blbExtHttpSrvrStatsEntry 21 }

httpSrvrNumIBDisabled OBJECT-TYPE
    SYNTAX     Counter32
    MAX-ACCESS read-only
    STATUS     current
    DESCRIPTION
           "Number of IB disables . "
    ::= { blbExtHttpSrvrStatsEntry 22 }

httpSrvrNumOOBDisabled OBJECT-TYPE
    SYNTAX     Counter32
    MAX-ACCESS read-only
    STATUS     current
    DESCRIPTION
           "Number of OOB disables. "
    ::= { blbExtHttpSrvrStatsEntry 23 }

httpSrvrNumOOBEnabled OBJECT-TYPE
    SYNTAX     Counter32
    MAX-ACCESS read-only
    STATUS     current
    DESCRIPTION
           "Number of OOB enables. "
    ::= { blbExtHttpSrvrStatsEntry 24 }

httpSrvrLastDisabledTime OBJECT-TYPE
    SYNTAX     TimeStamp
    MAX-ACCESS read-only
    STATUS     current
    DESCRIPTION
           "Last disabled time at server. "
    ::= { blbExtHttpSrvrStatsEntry 25 }

httpSrvrState OBJECT-TYPE
    SYNTAX     Integer32
    MAX-ACCESS read-only
    STATUS     current
    DESCRIPTION
           "Server state. "
    ::= { blbExtHttpSrvrStatsEntry 26 }

httpSrvrInBytes OBJECT-TYPE
    SYNTAX     Counter64
    MAX-ACCESS read-only
    STATUS     current
    DESCRIPTION
           "Total IN bytes. "
    ::= { blbExtHttpSrvrStatsEntry 27 }

httpSrvrOutBytes OBJECT-TYPE
    SYNTAX     Counter64
    MAX-ACCESS read-only
    STATUS     current
    DESCRIPTION
           "Total OUT bytes. "
    ::= { blbExtHttpSrvrStatsEntry 28 }



---
--blbExtSslSrvrStatsTable
---

blbExtSslSrvrStatsTable OBJECT-TYPE
    SYNTAX      SEQUENCE OF BlbExtSslSrvrStatsEntry
    MAX-ACCESS  not-accessible
    STATUS      current
    DESCRIPTION
        "A table of Ssl server stats. "
    ::= { blbExtStatsTraffic 6 }

blbExtSslSrvrStatsEntry OBJECT-TYPE
    SYNTAX     BlbExtSslSrvrStatsEntry 
    MAX-ACCESS  not-accessible
    STATUS      current
    DESCRIPTION
           "Ssl Server stats entry. "
    INDEX {sslSrvrSrvcAddressType, sslSrvrSrvcAddress, sslSrvrSrvcPort, sslSrvrAddressType, sslSrvrAddress, sslSrvrPort}
    ::= { blbExtSslSrvrStatsTable 1 }

BlbExtSslSrvrStatsEntry ::= SEQUENCE {
    sslSrvrSrvcAddressType        InetAddressType,
    sslSrvrSrvcAddress            InetAddress,
    sslSrvrSrvcPort               InetPortNumber,
    sslSrvrAddressType            InetAddressType,
    sslSrvrAddress                InetAddress,
    sslSrvrPort                   InetPortNumber,
    sslSrvrTotReqAccepted         Counter32,
    sslSrvrTotReqActive           Counter32,
    sslSrvrTotReqRejected         Counter32,
    sslSrvrTotSuccess             Counter32,
    sslSrvrTotRefused             Counter32,
    sslSrvrTotTimedout            Counter32,
    sslSrvrAvgReqPerConn          Counter32,
    sslSrvrTotResponse            Counter32,
    sslSrvrAvgResTime             Counter32,
    sslSrvrMaxResTime             Counter32,
    sslSrvrMinResTime             Counter32,
    sslSrvrNumReqEnqueue          Counter32,
    sslSrvrNumFreeConn            Counter32,
    sslSrvrNumOpeningConn         Counter32,
    sslSrvrNumConn                Counter32,
    sslSrvrNumIBDisabled          Counter32,
    sslSrvrNumOOBDisabled         Counter32,
    sslSrvrNumOOBEnabled          Counter32,
    sslSrvrLastDisabledTime       TimeStamp,
    sslSrvrState                  Integer32,
    sslSrvrInBytes                Counter64,
    sslSrvrOutBytes               Counter64
}

sslSrvrSrvcAddressType  OBJECT-TYPE
    SYNTAX     InetAddressType
    MAX-ACCESS not-accessible
    STATUS     current
    DESCRIPTION
           "The type of the service address, as defined
            in the InetAddress MIB. "
    REFERENCE "RFC 4001"
    ::= { blbExtSslSrvrStatsEntry 1 }

sslSrvrSrvcAddress  OBJECT-TYPE
    SYNTAX     InetAddress
    MAX-ACCESS not-accessible
    STATUS     current
    DESCRIPTION
           "The ssl service address. "
    ::= { blbExtSslSrvrStatsEntry 2 }

sslSrvrSrvcPort  OBJECT-TYPE
    SYNTAX     InetPortNumber
    MAX-ACCESS not-accessible
    STATUS     current
    DESCRIPTION
           "The port on which ssl service is listening. "
    ::= { blbExtSslSrvrStatsEntry 3 }

sslSrvrAddressType  OBJECT-TYPE
    SYNTAX     InetAddressType
    MAX-ACCESS not-accessible
    STATUS     current
    DESCRIPTION
           "The type of the server address, as defined
            in the InetAddress MIB. "
    REFERENCE "RFC 4001"
    ::= { blbExtSslSrvrStatsEntry 4 }

sslSrvrAddress  OBJECT-TYPE
    SYNTAX     InetAddress
    MAX-ACCESS not-accessible
    STATUS     current
    DESCRIPTION
           "The ssl server address. "
    ::= { blbExtSslSrvrStatsEntry 5 }

sslSrvrPort  OBJECT-TYPE
    SYNTAX     InetPortNumber
    MAX-ACCESS not-accessible
    STATUS     current
    DESCRIPTION
           "The port on which ssl server is listening. "
    ::= { blbExtSslSrvrStatsEntry 6 }

sslSrvrTotReqAccepted OBJECT-TYPE
    SYNTAX     Counter32
    MAX-ACCESS read-only
    STATUS     current
    DESCRIPTION
           "The total number of request accepted by ssl server. "
    ::= { blbExtSslSrvrStatsEntry 7 }

sslSrvrTotReqActive OBJECT-TYPE
    SYNTAX     Counter32
    MAX-ACCESS read-only
    STATUS     current
    DESCRIPTION
           "The total number of active request at server. "
    ::= { blbExtSslSrvrStatsEntry 8 }

sslSrvrTotReqRejected OBJECT-TYPE
    SYNTAX     Counter32
    MAX-ACCESS read-only
    STATUS     current
    DESCRIPTION
           "The total number of request rejected at server. "
    ::= { blbExtSslSrvrStatsEntry 9 }

sslSrvrTotSuccess OBJECT-TYPE
    SYNTAX     Counter32
    MAX-ACCESS read-only
    STATUS     current
    DESCRIPTION
           "The total number of request successfull at server. "
    ::= { blbExtSslSrvrStatsEntry 10 }

sslSrvrTotRefused OBJECT-TYPE
    SYNTAX     Counter32
    MAX-ACCESS read-only
    STATUS     current
    DESCRIPTION
           "The total number of request rejected at server. "
    ::= { blbExtSslSrvrStatsEntry 11 }

sslSrvrTotTimedout OBJECT-TYPE
    SYNTAX     Counter32
    MAX-ACCESS read-only
    STATUS     current
    DESCRIPTION
           "The total number of request timedout at server. "
    ::= { blbExtSslSrvrStatsEntry 12 }

sslSrvrAvgReqPerConn OBJECT-TYPE
    SYNTAX     Counter32
    MAX-ACCESS read-only
    STATUS     current
    DESCRIPTION
           "The average number of request per connection at server. "
    ::= { blbExtSslSrvrStatsEntry 13 }

sslSrvrTotResponse OBJECT-TYPE
    SYNTAX     Counter32
    MAX-ACCESS read-only
    STATUS     current
    DESCRIPTION
           "The total number of response at server. "
    ::= { blbExtSslSrvrStatsEntry 14 }

sslSrvrAvgResTime OBJECT-TYPE
    SYNTAX     Counter32
    MAX-ACCESS read-only
    STATUS     current
    DESCRIPTION
           "The average response time at server. "
    ::= { blbExtSslSrvrStatsEntry 15 }

sslSrvrMaxResTime OBJECT-TYPE
    SYNTAX     Counter32
    MAX-ACCESS read-only
    STATUS     current
    DESCRIPTION
           "The maximum response time at server. "
    ::= { blbExtSslSrvrStatsEntry 16 }

sslSrvrMinResTime OBJECT-TYPE
    SYNTAX     Counter32
    MAX-ACCESS read-only
    STATUS     current
    DESCRIPTION
           "The minimum response time at server. "
    ::= { blbExtSslSrvrStatsEntry 17 }

sslSrvrNumReqEnqueue OBJECT-TYPE
    SYNTAX     Counter32
    MAX-ACCESS read-only
    STATUS     current
    DESCRIPTION
           "The number of request enqueued at server. "
    ::= { blbExtSslSrvrStatsEntry 18 }

sslSrvrNumFreeConn OBJECT-TYPE
    SYNTAX     Counter32
    MAX-ACCESS read-only
    STATUS     current
    DESCRIPTION
           "Number of free connection at server. "
    ::= { blbExtSslSrvrStatsEntry 19 }

sslSrvrNumOpeningConn OBJECT-TYPE
    SYNTAX     Counter32
    MAX-ACCESS read-only
    STATUS     current
    DESCRIPTION
           "Number of opening connection at server. "
    ::= { blbExtSslSrvrStatsEntry 20 }

sslSrvrNumConn OBJECT-TYPE
    SYNTAX     Counter32
    MAX-ACCESS read-only
    STATUS     current
    DESCRIPTION
           "Number of connections at server. "
    ::= { blbExtSslSrvrStatsEntry 21 }

sslSrvrNumIBDisabled OBJECT-TYPE
    SYNTAX     Counter32
    MAX-ACCESS read-only
    STATUS     current
    DESCRIPTION
           "Number of IB disabled at server. "
    ::= { blbExtSslSrvrStatsEntry 22 }

sslSrvrNumOOBDisabled OBJECT-TYPE
    SYNTAX     Counter32
    MAX-ACCESS read-only
    STATUS     current
    DESCRIPTION
           "Number of OOB disabled at server. "
    ::= { blbExtSslSrvrStatsEntry 23 }

sslSrvrNumOOBEnabled OBJECT-TYPE
    SYNTAX     Counter32
    MAX-ACCESS read-only
    STATUS     current
    DESCRIPTION
           "Number of OOB enabled at server. "
    ::= { blbExtSslSrvrStatsEntry 24 }

sslSrvrLastDisabledTime OBJECT-TYPE
    SYNTAX     TimeStamp
    MAX-ACCESS read-only
    STATUS     current
    DESCRIPTION
           "Last disabled time at server. "
    ::= { blbExtSslSrvrStatsEntry 25 }

sslSrvrState OBJECT-TYPE
    SYNTAX     Integer32
    MAX-ACCESS read-only
    STATUS     current
    DESCRIPTION
           "Server state. "
    ::= { blbExtSslSrvrStatsEntry 26 }

sslSrvrInBytes OBJECT-TYPE
    SYNTAX     Counter64
    MAX-ACCESS read-only
    STATUS     current
    DESCRIPTION
           "Total IN bytes. "
    ::= { blbExtSslSrvrStatsEntry 27 }

sslSrvrOutBytes OBJECT-TYPE
    SYNTAX     Counter64
    MAX-ACCESS read-only
    STATUS     current
    DESCRIPTION
           "Total OUT bytes. "
    ::= { blbExtSslSrvrStatsEntry 28 }

---
--blbExtIpsReqSrvcStatsTable
---

blbExtIpsReqSrvcStatsTable OBJECT-TYPE
    SYNTAX      SEQUENCE OF BlbExtIpsReqSrvcStatsEntry
    MAX-ACCESS  not-accessible
    STATUS      current
    DESCRIPTION
        "A table of IPS request service stats. "
    ::= { blbExtStatsSecurity 1 }

blbExtIpsReqSrvcStatsEntry OBJECT-TYPE
    SYNTAX    BlbExtIpsReqSrvcStatsEntry 
    MAX-ACCESS  not-accessible
    STATUS      current
    DESCRIPTION
           "IPS request service stats entry. "
    INDEX {ipsReqSrvcAddressType, ipsReqSrvcAddress, ipsReqSrvcPort}
    ::= { blbExtIpsReqSrvcStatsTable 1 }

BlbExtIpsReqSrvcStatsEntry ::= SEQUENCE {
    ipsReqSrvcAddressType         InetAddressType,
    ipsReqSrvcAddress             InetAddress,
    ipsReqSrvcPort                InetPortNumber,
    ipsReqSrvcNoOfUrlProfMatched  Counter64,
    ipsReqSrvcNoOfAppProfViol     Counter64,
    ipsReqSrvcTotProfViol         Counter64
}

ipsReqSrvcAddressType OBJECT-TYPE
    SYNTAX     InetAddressType
    MAX-ACCESS not-accessible
    STATUS     current
    DESCRIPTION
           "The type of the service address, as defined
            in the InetAddress MIB. "
    REFERENCE "RFC 4001"
    ::= { blbExtIpsReqSrvcStatsEntry 1 }

ipsReqSrvcAddress OBJECT-TYPE
    SYNTAX     InetAddress
    MAX-ACCESS not-accessible
    STATUS     current
    DESCRIPTION
           "The service address. "
    ::= { blbExtIpsReqSrvcStatsEntry 2 }

ipsReqSrvcPort OBJECT-TYPE
    SYNTAX     InetPortNumber
    MAX-ACCESS not-accessible
    STATUS     current
    DESCRIPTION
           "The port on which ips service is listening. "
    ::= { blbExtIpsReqSrvcStatsEntry 3 }

ipsReqSrvcNoOfUrlProfMatched OBJECT-TYPE
    SYNTAX     Counter64
    MAX-ACCESS read-only
    STATUS     current
    DESCRIPTION
           "Number of URL profiles matched. "
    ::= { blbExtIpsReqSrvcStatsEntry 4 }

ipsReqSrvcNoOfAppProfViol OBJECT-TYPE
    SYNTAX     Counter64
    MAX-ACCESS read-only
    STATUS     current
    DESCRIPTION
           "Number of app profile violations. "
    ::= { blbExtIpsReqSrvcStatsEntry 5 }

ipsReqSrvcTotProfViol OBJECT-TYPE
    SYNTAX     Counter64
    MAX-ACCESS read-only
    STATUS     current
    DESCRIPTION
           "Total number of profile violations. "
    ::= { blbExtIpsReqSrvcStatsEntry 6 }


---
--blbExtIpsLrnSrvcStatsTable
---

blbExtIpsLrnSrvcStatsTable OBJECT-TYPE
    SYNTAX      SEQUENCE OF BlbExtIpsLrnSrvcStatsEntry
    MAX-ACCESS  not-accessible
    STATUS      current
    DESCRIPTION
        "A table of IPS request service stats. "
    ::= { blbExtStatsSecurity 2 }

blbExtIpsLrnSrvcStatsEntry OBJECT-TYPE
    SYNTAX    BlbExtIpsLrnSrvcStatsEntry 
    MAX-ACCESS  not-accessible
    STATUS      current
    DESCRIPTION
           "IPS request service stats entry. "
    INDEX {ipsLrnSrvcAddressType, ipsLrnSrvcAddress, ipsLrnSrvcPort}
    ::= { blbExtIpsLrnSrvcStatsTable 1 }

BlbExtIpsLrnSrvcStatsEntry ::= SEQUENCE {
    ipsLrnSrvcAddressType         InetAddressType,
    ipsLrnSrvcAddress             InetAddress,
    ipsLrnSrvcPort                InetPortNumber,
    ipsLrnSrvcUpdatesByReq        Counter64,
    ipsLrnSrvcUpdatesByRsp        Counter64,
    ipsLrnSrvcTotUpdatesByReq     Counter64,
    ipsLrnSrvcTotUpdatesByRsp     Counter64,
    ipsLrnSrvcTotUrlUpdated       Counter64,
    ipsLrnSrvcTotParamsLearned    Counter64,
    ipsLrnSrvcTimeLastUpdated     TimeStamp,
    ipsLrnSrvcTimeLocked          TimeStamp
}

ipsLrnSrvcAddressType OBJECT-TYPE
    SYNTAX     InetAddressType
    MAX-ACCESS not-accessible
    STATUS     current
    DESCRIPTION
           "The type of the service address, as defined
            in the InetAddress MIB. "
    REFERENCE "RFC 4001"
    ::= { blbExtIpsLrnSrvcStatsEntry 1 }

ipsLrnSrvcAddress OBJECT-TYPE
    SYNTAX     InetAddress
    MAX-ACCESS not-accessible
    STATUS     current
    DESCRIPTION
           "The service address. "
    ::= { blbExtIpsLrnSrvcStatsEntry 2 }

ipsLrnSrvcPort OBJECT-TYPE
    SYNTAX     InetPortNumber
    MAX-ACCESS not-accessible
    STATUS     current
    DESCRIPTION
           "The port on which ips service is listening. "
    ::= { blbExtIpsLrnSrvcStatsEntry 3 }

ipsLrnSrvcUpdatesByReq OBJECT-TYPE
    SYNTAX     Counter64
    MAX-ACCESS read-only
    STATUS     current
    DESCRIPTION
           "Number of updated by requests. "
    ::= { blbExtIpsLrnSrvcStatsEntry 4 }

ipsLrnSrvcUpdatesByRsp OBJECT-TYPE
    SYNTAX     Counter64
    MAX-ACCESS read-only
    STATUS     current
    DESCRIPTION
           "Number of updated by response. "
    ::= { blbExtIpsLrnSrvcStatsEntry 5 }

ipsLrnSrvcTotUpdatesByReq OBJECT-TYPE
    SYNTAX     Counter64
    MAX-ACCESS read-only
    STATUS     current
    DESCRIPTION
           "Total number of updated by requests. "
    ::= { blbExtIpsLrnSrvcStatsEntry 6 }

ipsLrnSrvcTotUpdatesByRsp OBJECT-TYPE
    SYNTAX     Counter64
    MAX-ACCESS read-only
    STATUS     current
    DESCRIPTION
           "Total number of updated by response. "
    ::= { blbExtIpsLrnSrvcStatsEntry 7 }

ipsLrnSrvcTotUrlUpdated OBJECT-TYPE
    SYNTAX     Counter64
    MAX-ACCESS read-only
    STATUS     current
    DESCRIPTION
           "Total number URL updated. "
    ::= { blbExtIpsLrnSrvcStatsEntry 8 }

ipsLrnSrvcTotParamsLearned OBJECT-TYPE
    SYNTAX     Counter64
    MAX-ACCESS read-only
    STATUS     current
    DESCRIPTION
           "Total number parameters learned. "
    ::= { blbExtIpsLrnSrvcStatsEntry 9 }

ipsLrnSrvcTimeLastUpdated OBJECT-TYPE
    SYNTAX     TimeStamp
    MAX-ACCESS read-only
    STATUS     current
    DESCRIPTION
           "Time at which last update was done. "
    ::= { blbExtIpsLrnSrvcStatsEntry 10 }

ipsLrnSrvcTimeLocked OBJECT-TYPE
    SYNTAX     TimeStamp
    MAX-ACCESS read-only
    STATUS     current
    DESCRIPTION
           "Time at which profile was locked. "
    ::= { blbExtIpsLrnSrvcStatsEntry 11 }


---
--blbExtIpsReqLimitStatsTable
---

blbExtIpsReqLimitStatsTable OBJECT-TYPE
    SYNTAX      SEQUENCE OF BlbExtIpsReqLimitStatsEntry
    MAX-ACCESS  not-accessible
    STATUS      current
    DESCRIPTION
        "A table of IPS request limit stats. "
    ::= { blbExtStatsSecurity 3 }

blbExtIpsReqLimitStatsEntry OBJECT-TYPE
    SYNTAX    BlbExtIpsReqLimitStatsEntry 
    MAX-ACCESS  not-accessible
    STATUS      current
    DESCRIPTION
           "IPS request limit stats entry. "
    INDEX {ipsReqLimitAddressType, ipsReqLimitAddress, ipsReqLimitPort}
    ::= { blbExtIpsReqLimitStatsTable 1 }

BlbExtIpsReqLimitStatsEntry ::= SEQUENCE {
    ipsReqLimitAddressType         InetAddressType,
    ipsReqLimitAddress             InetAddress,
    ipsReqLimitPort                InetPortNumber,
    ipsReqLimitUrlLenOFErr         Counter32,
    ipsReqLimitQueryLenOFErr       Counter32,
    ipsReqLimitReqLenOFErr         Counter32,
    ipsReqLimitCookieLenOFErr      Counter32,
    ipsReqLimitHdrCntOFErr         Counter32,
    ipsReqLimitHdrLenOFErr         Counter32,
    ipsReqLimitContentLenErr       Counter32,
    ipsReqLimitBlkdMethodErr       Counter32
}

ipsReqLimitAddressType OBJECT-TYPE
    SYNTAX     InetAddressType
    MAX-ACCESS not-accessible
    STATUS     current
    DESCRIPTION
           "The type of the service address, as defined
            in the InetAddress MIB. "
    REFERENCE "RFC 4001"
    ::= { blbExtIpsReqLimitStatsEntry 1 }

ipsReqLimitAddress OBJECT-TYPE
    SYNTAX     InetAddress
    MAX-ACCESS not-accessible
    STATUS     current
    DESCRIPTION
           "The service address. "
    ::= { blbExtIpsReqLimitStatsEntry 2 }

ipsReqLimitPort OBJECT-TYPE
    SYNTAX     InetPortNumber
    MAX-ACCESS not-accessible
    STATUS     current
    DESCRIPTION
           "The port on which ips service is listening. "
    ::= { blbExtIpsReqLimitStatsEntry 3 }

ipsReqLimitUrlLenOFErr OBJECT-TYPE
    SYNTAX     Counter32
    MAX-ACCESS read-only
    STATUS     current
    DESCRIPTION
           "Number of URL length overflow error. "
    ::= { blbExtIpsReqLimitStatsEntry 4 }

ipsReqLimitQueryLenOFErr OBJECT-TYPE
    SYNTAX     Counter32
    MAX-ACCESS read-only
    STATUS     current
    DESCRIPTION
           "Number of query length overflow error. "
    ::= { blbExtIpsReqLimitStatsEntry 5 }

ipsReqLimitReqLenOFErr OBJECT-TYPE
    SYNTAX     Counter32
    MAX-ACCESS read-only
    STATUS     current
    DESCRIPTION
           "Number of request length overflow error. "
    ::= { blbExtIpsReqLimitStatsEntry 6 }

ipsReqLimitCookieLenOFErr OBJECT-TYPE
    SYNTAX     Counter32
    MAX-ACCESS read-only
    STATUS     current
    DESCRIPTION
           "Number of Cookie length overflow error. "
    ::= { blbExtIpsReqLimitStatsEntry 7 }

ipsReqLimitHdrCntOFErr OBJECT-TYPE
    SYNTAX     Counter32
    MAX-ACCESS read-only
    STATUS     current
    DESCRIPTION
           "Number of header count overflow error. "
    ::= { blbExtIpsReqLimitStatsEntry 8 }

ipsReqLimitHdrLenOFErr OBJECT-TYPE
    SYNTAX     Counter32
    MAX-ACCESS read-only
    STATUS     current
    DESCRIPTION
           "Number of header length overflow error. "
    ::= { blbExtIpsReqLimitStatsEntry 9 }

ipsReqLimitContentLenErr OBJECT-TYPE
    SYNTAX     Counter32
    MAX-ACCESS read-only
    STATUS     current
    DESCRIPTION
           "Number of content length overflow error. "
    ::= { blbExtIpsReqLimitStatsEntry 10 }

ipsReqLimitBlkdMethodErr OBJECT-TYPE
    SYNTAX     Counter32
    MAX-ACCESS read-only
    STATUS     current
    DESCRIPTION
           "Number of blocked method error. "
    ::= { blbExtIpsReqLimitStatsEntry 11 }


---
--blbExtIpsUrlNormStatsTable
---

blbExtIpsUrlNormStatsTable OBJECT-TYPE
    SYNTAX      SEQUENCE OF BlbExtIpsUrlNormStatsEntry
    MAX-ACCESS  not-accessible
    STATUS      current
    DESCRIPTION
        "A table of IPS URL normalization stats. "
    ::= { blbExtStatsSecurity 4 }

blbExtIpsUrlNormStatsEntry OBJECT-TYPE
    SYNTAX    BlbExtIpsUrlNormStatsEntry 
    MAX-ACCESS  not-accessible
    STATUS      current
    DESCRIPTION
           "IPS URL normalization stats entry. "
    INDEX {ipsUrlNormAddressType, ipsUrlNormAddress, ipsUrlNormPort}
    ::= { blbExtIpsUrlNormStatsTable 1 }

BlbExtIpsUrlNormStatsEntry ::= SEQUENCE {
    ipsUrlNormAddressType         InetAddressType,
    ipsUrlNormAddress             InetAddress,
    ipsUrlNormPort                InetPortNumber,
    ipsUrlNormEncodingErr         Counter32,
    ipsUrlNormSlashDotInUrlErr    Counter32,
    ipsUrlNormTildaInUrl          Counter32,
    ipsUrlNormCharSetEncodingErr  Counter32
}

ipsUrlNormAddressType OBJECT-TYPE
    SYNTAX     InetAddressType
    MAX-ACCESS not-accessible
    STATUS     current
    DESCRIPTION
           "The type of the service address, as defined
            in the InetAddress MIB. "
    REFERENCE "RFC 4001"
    ::= { blbExtIpsUrlNormStatsEntry 1 }

ipsUrlNormAddress OBJECT-TYPE
    SYNTAX     InetAddress
    MAX-ACCESS not-accessible
    STATUS     current
    DESCRIPTION
           "The service address. "
    ::= { blbExtIpsUrlNormStatsEntry 2 }

ipsUrlNormPort OBJECT-TYPE
    SYNTAX     InetPortNumber
    MAX-ACCESS not-accessible
    STATUS     current
    DESCRIPTION
           "The port on which ips service is listening. "
    ::= { blbExtIpsUrlNormStatsEntry 3 }

ipsUrlNormEncodingErr OBJECT-TYPE
    SYNTAX     Counter32
    MAX-ACCESS read-only
    STATUS     current
    DESCRIPTION
           "Number of encoding error. "
    ::= { blbExtIpsUrlNormStatsEntry 4 }

ipsUrlNormSlashDotInUrlErr OBJECT-TYPE
    SYNTAX     Counter32
    MAX-ACCESS read-only
    STATUS     current
    DESCRIPTION
           "Number of slash dot in URL error. "
    ::= { blbExtIpsUrlNormStatsEntry 5 }

ipsUrlNormTildaInUrl OBJECT-TYPE
    SYNTAX     Counter32
    MAX-ACCESS read-only
    STATUS     current
    DESCRIPTION
           "Number of tilda in URL error. "
    ::= { blbExtIpsUrlNormStatsEntry 6 }

ipsUrlNormCharSetEncodingErr OBJECT-TYPE
    SYNTAX     Counter32
    MAX-ACCESS read-only
    STATUS     current
    DESCRIPTION
           "Number of character set encoding error. "
    ::= { blbExtIpsUrlNormStatsEntry 7 }



---
--blbExtIpsCookieSecStatsTable
---

blbExtIpsCookieSecStatsTable OBJECT-TYPE
    SYNTAX      SEQUENCE OF BlbExtIpsCookieSecStatsEntry
    MAX-ACCESS  not-accessible
    STATUS      current
    DESCRIPTION
        "A table of IPS cookie security stats. "
    ::= { blbExtStatsSecurity 5 }

blbExtIpsCookieSecStatsEntry OBJECT-TYPE
    SYNTAX    BlbExtIpsCookieSecStatsEntry 
    MAX-ACCESS  not-accessible
    STATUS      current
    DESCRIPTION
           "IPS cookie security stats entry. "
    INDEX {ipsCookieSecAddressType, ipsCookieSecAddress, ipsCookieSecPort}
    ::= { blbExtIpsCookieSecStatsTable 1 }

BlbExtIpsCookieSecStatsEntry ::= SEQUENCE {
    ipsCookieSecAddressType         InetAddressType,
    ipsCookieSecAddress             InetAddress,
    ipsCookieSecPort                InetPortNumber,
    ipsCookieSecEncrypted           Counter32,
    ipsCookieSecTampered            Counter32,
    ipsCookieSecNumCookieAllow      Counter32,
    ipsCookieSecNumCookieSet        Counter32,
    ipsCookieSecNumCookieErr        Counter32,
    ipsCookieSecCookieDecErr        Counter32,
    ipsCookieSecCookieDecrypted     Counter32
}

ipsCookieSecAddressType OBJECT-TYPE
    SYNTAX     InetAddressType
    MAX-ACCESS not-accessible
    STATUS     current
    DESCRIPTION
           "The type of the service address, as defined
            in the InetAddress MIB. "
    REFERENCE "RFC 4001"
    ::= { blbExtIpsCookieSecStatsEntry 1 }

ipsCookieSecAddress OBJECT-TYPE
    SYNTAX     InetAddress
    MAX-ACCESS not-accessible
    STATUS     current
    DESCRIPTION
           "The service address. "
    ::= { blbExtIpsCookieSecStatsEntry 2 }

ipsCookieSecPort OBJECT-TYPE
    SYNTAX     InetPortNumber
    MAX-ACCESS not-accessible
    STATUS     current
    DESCRIPTION
           "The port on which ips service is listening. "
    ::= { blbExtIpsCookieSecStatsEntry 3 }

ipsCookieSecEncrypted OBJECT-TYPE
    SYNTAX     Counter32
    MAX-ACCESS read-only
    STATUS     current
    DESCRIPTION
           "Number of cookie encrypted. "
    ::= { blbExtIpsCookieSecStatsEntry 4 }

ipsCookieSecTampered OBJECT-TYPE
    SYNTAX     Counter32
    MAX-ACCESS read-only
    STATUS     current
    DESCRIPTION
           "Number of cookie tampered. "
    ::= { blbExtIpsCookieSecStatsEntry 5 }

ipsCookieSecNumCookieAllow OBJECT-TYPE
    SYNTAX     Counter32
    MAX-ACCESS read-only
    STATUS     current
    DESCRIPTION
           "Number of cookie allowed. "
    ::= { blbExtIpsCookieSecStatsEntry 6 }

ipsCookieSecNumCookieSet OBJECT-TYPE
    SYNTAX     Counter32
    MAX-ACCESS read-only
    STATUS     current
    DESCRIPTION
           "Number of cookie set. "
    ::= { blbExtIpsCookieSecStatsEntry 7 }

ipsCookieSecNumCookieErr OBJECT-TYPE
    SYNTAX     Counter32
    MAX-ACCESS read-only
    STATUS     current
    DESCRIPTION
           "Number of cookie error. "
    ::= { blbExtIpsCookieSecStatsEntry 8 }

ipsCookieSecCookieDecErr OBJECT-TYPE
    SYNTAX     Counter32
    MAX-ACCESS read-only
    STATUS     current
    DESCRIPTION
           "Number of cookie dec error. "
    ::= { blbExtIpsCookieSecStatsEntry 9 }

ipsCookieSecCookieDecrypted OBJECT-TYPE
    SYNTAX     Counter32
    MAX-ACCESS read-only
    STATUS     current
    DESCRIPTION
           "Number of cookie decrypted. "
    ::= { blbExtIpsCookieSecStatsEntry 10 }




---
--blbExtIpsUrlAclStatsTable
---

blbExtIpsUrlAclStatsTable OBJECT-TYPE
    SYNTAX      SEQUENCE OF BlbExtIpsUrlAclStatsEntry
    MAX-ACCESS  not-accessible
    STATUS      current
    DESCRIPTION
        "A table of IPS URL ACLstats. "
    ::= { blbExtStatsSecurity 6 }

blbExtIpsUrlAclStatsEntry OBJECT-TYPE
    SYNTAX    BlbExtIpsUrlAclStatsEntry 
    MAX-ACCESS  not-accessible
    STATUS      current
    DESCRIPTION
           "IPS URL ACL stats entry. "
    INDEX {ipsUrlAclAddressType, ipsUrlAclAddress, ipsUrlAclPort}
    ::= { blbExtIpsUrlAclStatsTable 1 }

BlbExtIpsUrlAclStatsEntry ::= SEQUENCE {
    ipsUrlAclAddressType         InetAddressType,
    ipsUrlAclAddress             InetAddress,
    ipsUrlAclPort                InetPortNumber,
    ipsUrlAclProcessAclHits      Counter32,
    ipsUrlAclPolicyHits          Counter32,
    ipsUrlAclTimeStamp           TimeStamp,
    ipsUrlAclReserved            OCTET STRING,
    ipsUrlAclAllowAclHits        Counter32
}

ipsUrlAclAddressType OBJECT-TYPE
    SYNTAX     InetAddressType
    MAX-ACCESS not-accessible
    STATUS     current
    DESCRIPTION
           "The type of the service address, as defined
            in the InetAddress MIB. "
    REFERENCE "RFC 4001"
    ::= { blbExtIpsUrlAclStatsEntry 1 }

ipsUrlAclAddress OBJECT-TYPE
    SYNTAX     InetAddress
    MAX-ACCESS not-accessible
    STATUS     current
    DESCRIPTION
           "The service address. "
    ::= { blbExtIpsUrlAclStatsEntry 2 }

ipsUrlAclPort OBJECT-TYPE
    SYNTAX    InetPortNumber 
    MAX-ACCESS not-accessible
    STATUS     current
    DESCRIPTION
           "The port on which ips service is listening. "
    ::= { blbExtIpsUrlAclStatsEntry 3 }

ipsUrlAclProcessAclHits OBJECT-TYPE
    SYNTAX     Counter32
    MAX-ACCESS read-only
    STATUS     current
    DESCRIPTION
           "Number of ACL hits. "
    ::= { blbExtIpsUrlAclStatsEntry 4 }

ipsUrlAclPolicyHits OBJECT-TYPE
    SYNTAX     Counter32
    MAX-ACCESS read-only
    STATUS     current
    DESCRIPTION
           "Number of ACL policy hits. "
    ::= { blbExtIpsUrlAclStatsEntry 5 }

ipsUrlAclTimeStamp OBJECT-TYPE
    SYNTAX     TimeStamp
    MAX-ACCESS read-only
    STATUS     current
    DESCRIPTION
           "Time stamp at which this entry was last modified. "
    ::= { blbExtIpsUrlAclStatsEntry 6 }

ipsUrlAclReserved OBJECT-TYPE
    SYNTAX     OCTET STRING
    MAX-ACCESS read-only
    STATUS     current
    DESCRIPTION
           "Reserved. "
    ::= { blbExtIpsUrlAclStatsEntry 7 }

ipsUrlAclAllowAclHits OBJECT-TYPE
    SYNTAX     Counter32
    MAX-ACCESS read-only
    STATUS     current
    DESCRIPTION
           "Number of ACL policy hits. "
    ::= { blbExtIpsUrlAclStatsEntry 8 }


---
--blbExtIpsHdrAclStatsTable
---

blbExtIpsHdrAclStatsTable OBJECT-TYPE
    SYNTAX      SEQUENCE OF BlbExtIpsHdrAclStatsEntry
    MAX-ACCESS  not-accessible
    STATUS      current
    DESCRIPTION
        "A table of IPS header ACL stats. "
    ::= { blbExtStatsSecurity 7 }

blbExtIpsHdrAclStatsEntry OBJECT-TYPE
    SYNTAX    BlbExtIpsHdrAclStatsEntry 
    MAX-ACCESS  not-accessible
    STATUS      current
    DESCRIPTION
           "IPS header ACL stats entry. "
    INDEX {ipsHdrAclAddressType, ipsHdrAclAddress, ipsHdrAclPort}
    ::= { blbExtIpsHdrAclStatsTable 1 }

BlbExtIpsHdrAclStatsEntry ::= SEQUENCE {
    ipsHdrAclAddressType         InetAddressType,
    ipsHdrAclAddress             InetAddress,
    ipsHdrAclPort                InetPortNumber,
    ipsHdrAclHits                Counter32,
    ipsHdrAclTimeStamp           TimeStamp
}

ipsHdrAclAddressType OBJECT-TYPE
    SYNTAX     InetAddressType
    MAX-ACCESS not-accessible
    STATUS     current
    DESCRIPTION
           "The type of the service address, as defined
            in the InetAddress MIB. "
    REFERENCE "RFC 4001"
    ::= { blbExtIpsHdrAclStatsEntry 1 }

ipsHdrAclAddress OBJECT-TYPE
    SYNTAX     InetAddress
    MAX-ACCESS not-accessible
    STATUS     current
    DESCRIPTION
           "The service address. "
    ::= { blbExtIpsHdrAclStatsEntry 2 }

ipsHdrAclPort OBJECT-TYPE
    SYNTAX     InetPortNumber
    MAX-ACCESS not-accessible
    STATUS     current
    DESCRIPTION
           "The port on which ips service is listening. "
    ::= { blbExtIpsHdrAclStatsEntry 3 }

ipsHdrAclHits OBJECT-TYPE
    SYNTAX     Counter32
    MAX-ACCESS read-only
    STATUS     current
    DESCRIPTION
           "Number of ACL hits. "
    ::= { blbExtIpsHdrAclStatsEntry 4 }

ipsHdrAclTimeStamp OBJECT-TYPE
    SYNTAX     TimeStamp
    MAX-ACCESS read-only
    STATUS     current
    DESCRIPTION
           "Time stamp at which this entry was last modified. "
    ::= { blbExtIpsHdrAclStatsEntry 5 }




---
--blbExtIpsWebAddrTransStatsTable
---

blbExtIpsWebAddrTransStatsTable OBJECT-TYPE
    SYNTAX      SEQUENCE OF BlbExtIpsWebAddrTransStatsEntry
    MAX-ACCESS  not-accessible
    STATUS      current
    DESCRIPTION
        "A table of IPS header ACL stats. "
    ::= { blbExtStatsSecurity 8 }

blbExtIpsWebAddrTransStatsEntry OBJECT-TYPE
    SYNTAX    BlbExtIpsWebAddrTransStatsEntry 
    MAX-ACCESS  not-accessible
    STATUS      current
    DESCRIPTION
           "IPS header ACL stats entry. "
    INDEX {ipsWebAddrTransAddressType, ipsWebAddrTransAddress, ipsWebAddrTransPort}
    ::= { blbExtIpsWebAddrTransStatsTable 1 }

BlbExtIpsWebAddrTransStatsEntry ::= SEQUENCE {
    ipsWebAddrTransAddressType         InetAddressType,
    ipsWebAddrTransAddress             InetAddress,
    ipsWebAddrTransPort                InetPortNumber,
    ipsWebAddrTransReqUrlTrans         Counter32,
    ipsWebAddrTransRspUrlTrans         Counter32,
    ipsWebAddrTransReqUrlReWritten     Counter32,
    ipsWebAddrTransReqHdrReWritten     Counter32,
    ipsWebAddrTransRspHdrReWritten     Counter32,
    ipsWebAddrTransReqReDirection      Counter32,
    ipsWebAddrTransTimeStamp           TimeStamp
}

ipsWebAddrTransAddressType OBJECT-TYPE
    SYNTAX     InetAddressType
    MAX-ACCESS not-accessible
    STATUS     current
    DESCRIPTION
           "The type of the service address, as defined
            in the InetAddress MIB. "
    REFERENCE "RFC 4001"
    ::= { blbExtIpsWebAddrTransStatsEntry 1 }

ipsWebAddrTransAddress OBJECT-TYPE
    SYNTAX     InetAddress
    MAX-ACCESS not-accessible
    STATUS     current
    DESCRIPTION
           "The service address. "
    ::= { blbExtIpsWebAddrTransStatsEntry 2 }

ipsWebAddrTransPort OBJECT-TYPE
    SYNTAX     InetPortNumber
    MAX-ACCESS not-accessible
    STATUS     current
    DESCRIPTION
           "The port on which ips service is listening. "
    ::= { blbExtIpsWebAddrTransStatsEntry 3 }

ipsWebAddrTransReqUrlTrans OBJECT-TYPE
    SYNTAX     Counter32
    MAX-ACCESS read-only
    STATUS     current
    DESCRIPTION
           "Number of URL translation requests. "
    ::= { blbExtIpsWebAddrTransStatsEntry 4 }

ipsWebAddrTransRspUrlTrans OBJECT-TYPE
    SYNTAX     Counter32
    MAX-ACCESS read-only
    STATUS     current
    DESCRIPTION
           "Number of URL translation response. "
    ::= { blbExtIpsWebAddrTransStatsEntry 5 }

ipsWebAddrTransReqUrlReWritten OBJECT-TYPE
    SYNTAX     Counter32
    MAX-ACCESS read-only
    STATUS     current
    DESCRIPTION
           "Number of URL re-written. "
    ::= { blbExtIpsWebAddrTransStatsEntry 6 }

ipsWebAddrTransReqHdrReWritten OBJECT-TYPE
    SYNTAX     Counter32
    MAX-ACCESS read-only
    STATUS     current
    DESCRIPTION
           "Number of request header re-written. "
    ::= { blbExtIpsWebAddrTransStatsEntry 7 }

ipsWebAddrTransRspHdrReWritten OBJECT-TYPE
    SYNTAX     Counter32
    MAX-ACCESS read-only
    STATUS     current
    DESCRIPTION
           "Number of response header re-written. "
    ::= { blbExtIpsWebAddrTransStatsEntry 8 }

ipsWebAddrTransReqReDirection OBJECT-TYPE
    SYNTAX     Counter32
    MAX-ACCESS read-only
    STATUS     current
    DESCRIPTION
           "Number of request redirection. "
    ::= { blbExtIpsWebAddrTransStatsEntry 9 }

ipsWebAddrTransTimeStamp OBJECT-TYPE
    SYNTAX     TimeStamp
    MAX-ACCESS read-only
    STATUS     current
    DESCRIPTION
           "Time stamp at which this entry was last modified. "
    ::= { blbExtIpsWebAddrTransStatsEntry 10 }



---
--blbExtIpsAccessCtrlStatsTable
---

blbExtIpsAccessCtrlStatsTable OBJECT-TYPE
    SYNTAX      SEQUENCE OF BlbExtIpsAccessCtrlStatsEntry
    MAX-ACCESS  not-accessible
    STATUS      current
    DESCRIPTION
        "A table of IPS access control stats. "
    ::= { blbExtStatsSecurity 9 }

blbExtIpsAccessCtrlStatsEntry OBJECT-TYPE
    SYNTAX    BlbExtIpsAccessCtrlStatsEntry 
    MAX-ACCESS  not-accessible
    STATUS      current
    DESCRIPTION
           "IPS access control stats entry. "
    INDEX {ipsAccessCtrlAddressType, ipsAccessCtrlAddress, ipsAccessCtrlPort}
    ::= { blbExtIpsAccessCtrlStatsTable 1 }

BlbExtIpsAccessCtrlStatsEntry ::= SEQUENCE {
    ipsAccessCtrlAddressType         InetAddressType,
    ipsAccessCtrlAddress             InetAddress,
    ipsAccessCtrlPort                InetPortNumber,
    ipsAccessCtrlMissingCookie       Counter32,
    ipsAccessCtrlNoAuthHdr           Counter32,
    ipsAccessCtrlInvalidCookie       Counter32,
    ipsAccessCtrlExpiredCookie       Counter32,
    ipsAccessCtrlAccessDenied        Counter32,
    ipsAccessCtrlGenFailure          Counter32,
    ipsAccessCtrlAccessAttempts      Counter32,
    ipsAccessCtrlAccessAttemptsTotRtt Counter32,
    ipsAccessCtrlInvalidSrcIp        Counter32,
    ipsAccessCtrlAuthCacheHits       Counter32,
    ipsAccessCtrlAuthCacheMiss       Counter32,
    ipsAccessCtrlAuthCacheExp        Counter32,
    ipsAccessCtrlTimeStamp           TimeStamp
}

ipsAccessCtrlAddressType OBJECT-TYPE
    SYNTAX     InetAddressType
    MAX-ACCESS not-accessible
    STATUS     current
    DESCRIPTION
           "The type of the service address, as defined
            in the InetAddress MIB. "
    REFERENCE "RFC 4001"
    ::= { blbExtIpsAccessCtrlStatsEntry 1 }

ipsAccessCtrlAddress OBJECT-TYPE
    SYNTAX     InetAddress
    MAX-ACCESS not-accessible
    STATUS     current
    DESCRIPTION
           "The service address. "
    ::= { blbExtIpsAccessCtrlStatsEntry 2 }

ipsAccessCtrlPort OBJECT-TYPE
    SYNTAX     InetPortNumber
    MAX-ACCESS not-accessible
    STATUS     current
    DESCRIPTION
           "The port on which ips service is listening. "
    ::= { blbExtIpsAccessCtrlStatsEntry 3 }

ipsAccessCtrlMissingCookie OBJECT-TYPE
    SYNTAX     Counter32
    MAX-ACCESS read-only
    STATUS     current
    DESCRIPTION
           "Number of missing cookies. "
    ::= { blbExtIpsAccessCtrlStatsEntry 4 }

ipsAccessCtrlNoAuthHdr OBJECT-TYPE
    SYNTAX     Counter32
    MAX-ACCESS read-only
    STATUS     current
    DESCRIPTION
           "Number of no authorization header. "
    ::= { blbExtIpsAccessCtrlStatsEntry 5 }

ipsAccessCtrlInvalidCookie OBJECT-TYPE
    SYNTAX     Counter32
    MAX-ACCESS read-only
    STATUS     current
    DESCRIPTION
           "Number of invalid cookie. "
    ::= { blbExtIpsAccessCtrlStatsEntry 6 }

ipsAccessCtrlExpiredCookie OBJECT-TYPE
    SYNTAX     Counter32
    MAX-ACCESS read-only
    STATUS     current
    DESCRIPTION
           "Number of expired cookie. "
    ::= { blbExtIpsAccessCtrlStatsEntry 7 }

ipsAccessCtrlAccessDenied OBJECT-TYPE
    SYNTAX     Counter32
    MAX-ACCESS read-only
    STATUS     current
    DESCRIPTION
           "Number of access denied. "
    ::= { blbExtIpsAccessCtrlStatsEntry 8 }

ipsAccessCtrlGenFailure OBJECT-TYPE
    SYNTAX     Counter32
    MAX-ACCESS read-only
    STATUS     current
    DESCRIPTION
           "Number of general failure. "
    ::= { blbExtIpsAccessCtrlStatsEntry 9 }

ipsAccessCtrlAccessAttempts OBJECT-TYPE
    SYNTAX     Counter32
    MAX-ACCESS read-only
    STATUS     current
    DESCRIPTION
           "Number of access attempts. "
    ::= { blbExtIpsAccessCtrlStatsEntry 10 }

ipsAccessCtrlAccessAttemptsTotRtt OBJECT-TYPE
    SYNTAX     Counter32
    MAX-ACCESS read-only
    STATUS     current
    DESCRIPTION
           "Number of access attempts. "
    ::= { blbExtIpsAccessCtrlStatsEntry 11 }

ipsAccessCtrlInvalidSrcIp OBJECT-TYPE
    SYNTAX     Counter32
    MAX-ACCESS read-only
    STATUS     current
    DESCRIPTION
           "Number of invalid source ip. "
    ::= { blbExtIpsAccessCtrlStatsEntry 12 }

ipsAccessCtrlAuthCacheHits OBJECT-TYPE
    SYNTAX     Counter32
    MAX-ACCESS read-only
    STATUS     current
    DESCRIPTION
           "Number of authorization cache hits. "
    ::= { blbExtIpsAccessCtrlStatsEntry 13 }

ipsAccessCtrlAuthCacheMiss OBJECT-TYPE
    SYNTAX     Counter32
    MAX-ACCESS read-only
    STATUS     current
    DESCRIPTION
           "Number of authorization cache miss. "
    ::= { blbExtIpsAccessCtrlStatsEntry 14 }

ipsAccessCtrlAuthCacheExp OBJECT-TYPE
    SYNTAX     Counter32
    MAX-ACCESS read-only
    STATUS     current
    DESCRIPTION
           "Number of authorization cache expiry. "
    ::= { blbExtIpsAccessCtrlStatsEntry 15 }

ipsAccessCtrlTimeStamp OBJECT-TYPE
    SYNTAX     TimeStamp
    MAX-ACCESS read-only
    STATUS     current
    DESCRIPTION
           "Time stamp at which this entry was last modified. "
    ::= { blbExtIpsAccessCtrlStatsEntry 16 }





---
--blbExtIpsRCStatsTable
---

blbExtIpsRCStatsTable OBJECT-TYPE
    SYNTAX      SEQUENCE OF BlbExtIpsRCStatsEntry
    MAX-ACCESS  not-accessible
    STATUS      current
    DESCRIPTION
        "A table of IPS rate control stats. "
    ::= { blbExtStatsSecurity 10 }

blbExtIpsRCStatsEntry OBJECT-TYPE
    SYNTAX    BlbExtIpsRCStatsEntry 
    MAX-ACCESS  not-accessible
    STATUS      current
    DESCRIPTION
           "IPS rate control stats entry. "
    INDEX {ipsRCAddressType, ipsRCAddress, ipsRCPort}
    ::= { blbExtIpsRCStatsTable 1 }

BlbExtIpsRCStatsEntry ::= SEQUENCE {
    ipsRCAddressType         InetAddressType,
    ipsRCAddress             InetAddress,
    ipsRCPort                InetPortNumber,
    ipsRCTotServed           Counter32,
    ipsRCTotQueued           Counter32,
    ipsRCTotDropped          Counter32,
    ipsRCTotOutOfResource    Counter32,
    ipsRCTimeStamp           TimeStamp
}

ipsRCAddressType OBJECT-TYPE
    SYNTAX     InetAddressType
    MAX-ACCESS not-accessible
    STATUS     current
    DESCRIPTION
           "The type of the service address, as defined
            in the InetAddress MIB. "
    REFERENCE "RFC 4001"
    ::= { blbExtIpsRCStatsEntry 1 }

ipsRCAddress OBJECT-TYPE
    SYNTAX     InetAddress
    MAX-ACCESS not-accessible
    STATUS     current
    DESCRIPTION
           "The service address. "
    ::= { blbExtIpsRCStatsEntry 2 }

ipsRCPort OBJECT-TYPE
    SYNTAX     InetPortNumber
    MAX-ACCESS not-accessible
    STATUS     current
    DESCRIPTION
           "The port on which ips service is listening. "
    ::= { blbExtIpsRCStatsEntry 3 }

ipsRCTotServed OBJECT-TYPE
    SYNTAX     Counter32
    MAX-ACCESS read-only
    STATUS     current
    DESCRIPTION
           "Total number of RC served. "
    ::= { blbExtIpsRCStatsEntry 4 }

ipsRCTotQueued OBJECT-TYPE
    SYNTAX     Counter32
    MAX-ACCESS read-only
    STATUS     current
    DESCRIPTION
           "Total number RC queued. "
    ::= { blbExtIpsRCStatsEntry 5 }

ipsRCTotDropped OBJECT-TYPE
    SYNTAX     Counter32
    MAX-ACCESS read-only
    STATUS     current
    DESCRIPTION
           "Total number RC dropped. "
    ::= { blbExtIpsRCStatsEntry 6 }

ipsRCTotOutOfResource OBJECT-TYPE
    SYNTAX     Counter32
    MAX-ACCESS read-only
    STATUS     current
    DESCRIPTION
           "Total number of out of resource error. "
    ::= { blbExtIpsRCStatsEntry 7 }

ipsRCTimeStamp OBJECT-TYPE
    SYNTAX     TimeStamp
    MAX-ACCESS read-only
    STATUS     current
    DESCRIPTION
           "Time stamp at which this entry was last modified. "
    ::= { blbExtIpsRCStatsEntry 8 }




---
--blbExtIpsUrlPolicyStatsTable
---

blbExtIpsUrlPolicyStatsTable OBJECT-TYPE
    SYNTAX      SEQUENCE OF BlbExtIpsUrlPolicyStatsEntry
    MAX-ACCESS  not-accessible
    STATUS      current
    DESCRIPTION
        "A table of IPS UrlPolicy stats. "
    ::= { blbExtStatsSecurity 11 }

blbExtIpsUrlPolicyStatsEntry OBJECT-TYPE
    SYNTAX    BlbExtIpsUrlPolicyStatsEntry 
    MAX-ACCESS  not-accessible
    STATUS      current
    DESCRIPTION
           "IPS UrlPolicy stats entry. "
    INDEX {ipsUrlPolicyAddressType, ipsUrlPolicyAddress, ipsUrlPolicyPort}
    ::= { blbExtIpsUrlPolicyStatsTable 1 }

BlbExtIpsUrlPolicyStatsEntry ::= SEQUENCE {
    ipsUrlPolicyAddressType         InetAddressType,
    ipsUrlPolicyAddress             InetAddress,
    ipsUrlPolicyPort                InetPortNumber,
    ipsUrlPolicyTotServed           Counter32,
    ipsUrlPolicyTotQueued           Counter32,
    ipsUrlPolicyTotDropped          Counter32,
    ipsUrlPolicyTotOutOfResource    Counter32,
    ipsUrlPolicyEntryCtrlAuth       Counter32,
    ipsUrlPolicyTimeStamp           TimeStamp
}

ipsUrlPolicyAddressType OBJECT-TYPE
    SYNTAX     InetAddressType
    MAX-ACCESS not-accessible
    STATUS     current
    DESCRIPTION
           "The type of the service address, as defined
            in the InetAddress MIB. "
    REFERENCE "RFC 4001"
    ::= { blbExtIpsUrlPolicyStatsEntry 1 }

ipsUrlPolicyAddress OBJECT-TYPE
    SYNTAX     InetAddress
    MAX-ACCESS not-accessible
    STATUS     current
    DESCRIPTION
           "The service address. "
    ::= { blbExtIpsUrlPolicyStatsEntry 2 }

ipsUrlPolicyPort OBJECT-TYPE
    SYNTAX     InetPortNumber
    MAX-ACCESS not-accessible
    STATUS     current
    DESCRIPTION
           "The port on which ips service is listening. "
    ::= { blbExtIpsUrlPolicyStatsEntry 3 }

ipsUrlPolicyTotServed OBJECT-TYPE
    SYNTAX     Counter32
    MAX-ACCESS read-only
    STATUS     current
    DESCRIPTION
           "Total number of UrlPolicy served. "
    ::= { blbExtIpsUrlPolicyStatsEntry 4 }

ipsUrlPolicyTotQueued OBJECT-TYPE
    SYNTAX     Counter32
    MAX-ACCESS read-only
    STATUS     current
    DESCRIPTION
           "Total number UrlPolicy queued. "
    ::= { blbExtIpsUrlPolicyStatsEntry 5 }

ipsUrlPolicyTotDropped OBJECT-TYPE
    SYNTAX     Counter32
    MAX-ACCESS read-only
    STATUS     current
    DESCRIPTION
           "Total number UrlPolicy dropped. "
    ::= { blbExtIpsUrlPolicyStatsEntry 6 }

ipsUrlPolicyTotOutOfResource OBJECT-TYPE
    SYNTAX     Counter32
    MAX-ACCESS read-only
    STATUS     current
    DESCRIPTION
           "Total number of out of resource error. "
    ::= { blbExtIpsUrlPolicyStatsEntry 7 }

ipsUrlPolicyEntryCtrlAuth OBJECT-TYPE
    SYNTAX     Counter32
    MAX-ACCESS read-only
    STATUS     current
    DESCRIPTION
           "Total number entry control authentication. "
    ::= { blbExtIpsUrlPolicyStatsEntry 8 }


ipsUrlPolicyTimeStamp OBJECT-TYPE
    SYNTAX     TimeStamp
    MAX-ACCESS read-only
    STATUS     current
    DESCRIPTION
           "Time stamp at which this entry was last modified. "
    ::= { blbExtIpsUrlPolicyStatsEntry 9 }


blbExtHttpProxySecStatsTable OBJECT-TYPE
    SYNTAX      SEQUENCE OF BlbExtHttpProxySecStatsEntry
    MAX-ACCESS  not-accessible
    STATUS      current
    DESCRIPTION
        "A table of HTTP proxy security stats. "
    ::= { blbExtStatsSecurity 12 }

blbExtHttpProxySecStatsEntry OBJECT-TYPE
    SYNTAX     BlbExtHttpProxySecStatsEntry 
    MAX-ACCESS  not-accessible
    STATUS      current
    DESCRIPTION
           "HTTP proxy stats entry. "
    INDEX {httpProxySecAddressType, httpProxySecAddress, httpProxySecPort}
    ::= { blbExtHttpProxySecStatsTable 1 }

BlbExtHttpProxySecStatsEntry ::= SEQUENCE {
    httpProxySecAddressType            InetAddressType,
    httpProxySecAddress                InetAddress,
    httpProxySecPort                   InetPortNumber,
    httpProxySecWAFBlockedIntrusions   Counter32,
    httpProxySecWAFMonitoredIntrusions Counter32,
    httpProxySecWAFWarnings            Counter32
} 

httpProxySecAddressType  OBJECT-TYPE
    SYNTAX     InetAddressType
    MAX-ACCESS not-accessible
    STATUS     current
    DESCRIPTION
           "The type of the http Proxy address, as defined
            in the InetAddress MIB. "
    REFERENCE "RFC 4001"
    ::= { blbExtHttpProxySecStatsEntry 1 }

httpProxySecAddress  OBJECT-TYPE
    SYNTAX     InetAddress
    MAX-ACCESS not-accessible
    STATUS     current
    DESCRIPTION
           "The http Proxy address. "
    ::= { blbExtHttpProxySecStatsEntry 2 }

httpProxySecPort  OBJECT-TYPE
    SYNTAX     InetPortNumber
    MAX-ACCESS not-accessible
    STATUS     current
    DESCRIPTION
           "The port on which http Proxy is listening. "
    ::= { blbExtHttpProxySecStatsEntry 3 }

httpProxySecWAFBlockedIntrusions OBJECT-TYPE
    SYNTAX     Counter32
    MAX-ACCESS read-only
    STATUS     current
    DESCRIPTION
           "Total number of WAF blocked intrusions. "
    ::= { blbExtHttpProxySecStatsEntry 4 }

httpProxySecWAFMonitoredIntrusions OBJECT-TYPE
    SYNTAX     Counter32
    MAX-ACCESS read-only
    STATUS     current
    DESCRIPTION
           "Total number of WAF monitored intrusions. "
    ::= { blbExtHttpProxySecStatsEntry 5 }

httpProxySecWAFWarnings OBJECT-TYPE
    SYNTAX     Counter32
    MAX-ACCESS read-only
    STATUS     current
    DESCRIPTION
           "Total number of WAF warnings. "
    ::= { blbExtHttpProxySecStatsEntry 6 }


---
--blbExtSMUserSessionTable
---
blbExtSMUserSessionTable OBJECT-TYPE
    SYNTAX      SEQUENCE OF BlbExtSMUserSessionEntry
    MAX-ACCESS  not-accessible
    STATUS      current
    DESCRIPTION
        "A table of siteminder user session info. "
    ::= { blbExtStatsAAA 1 }

blbExtSMUserSessionEntry OBJECT-TYPE
    SYNTAX   BlbExtSMUserSessionEntry 
    MAX-ACCESS  not-accessible
    STATUS      current
    DESCRIPTION
           "siteminder user session info entry. "
    INDEX {smRealmName}
    ::= { blbExtSMUserSessionTable 1 }

BlbExtSMUserSessionEntry ::= SEQUENCE {
    smRealmName                     OCTET STRING,
    smAgentName                    OCTET STRING,
    smNumUserSessions               Integer32
} 

smRealmName OBJECT-TYPE
    SYNTAX    OCTET STRING (SIZE (1..30))
    MAX-ACCESS not-accessible
    STATUS     current
    DESCRIPTION
           "The realm name."
    ::= { blbExtSMUserSessionEntry 1 }

smAgentName OBJECT-TYPE
    SYNTAX     OCTET STRING (SIZE (1..30))
    MAX-ACCESS read-only
    STATUS     current
    DESCRIPTION
           "The agent name. "
    ::= { blbExtSMUserSessionEntry 2 }

smNumUserSessions OBJECT-TYPE
    SYNTAX     Integer32
    MAX-ACCESS read-only
    STATUS     current
    DESCRIPTION
           "Number of user sessions. "
    ::= { blbExtSMUserSessionEntry 3 }

---
-- blbExtStatsSystem
---

blbCPUTemperature   OBJECT-TYPE
   SYNTAX      OCTET STRING 
   MAX-ACCESS  read-only
   STATUS      current
   DESCRIPTION
         "Indicates the CPU temperature in degree-celcius."
   ::= { blbExtStatsSystem  1 }

blbSystemLoad       OBJECT-TYPE
   SYNTAX      Integer32
   MAX-ACCESS  read-only
   STATUS      current
   DESCRIPTION
        "Indicates the system load, in %tage."
   ::= { blbExtStatsSystem 2 }

blbFirmwareStorage  OBJECT-TYPE
   SYNTAX      OCTET STRING
   MAX-ACCESS  read-only
   STATUS      current
   DESCRIPTION
       "Indicates the space occupied by firmware, in %tage."
   ::= { blbExtStatsSystem 3 }

blbMailLogStorage   OBJECT-TYPE
   SYNTAX      OCTET STRING
   MAX-ACCESS  read-only
   STATUS      current
   DESCRIPTION
       "Indicates current space utilization of mail/log."
   ::= { blbExtStatsSystem 4 }

blbSystemActiveServices OBJECT-TYPE
   SYNTAX      Integer32
   MAX-ACCESS  read-only
   STATUS      current
   DESCRIPTION
       "The Barracuda Load Balancer's active services."
   ::= { blbExtStatsSystem 5 }

blbSystemOperatingServers OBJECT-TYPE
   SYNTAX      Integer32
   MAX-ACCESS  read-only
   STATUS      current
   DESCRIPTION
       "The Barracuda Load Balancer's operating servers."
  ::= { blbExtStatsSystem 6 }

blbClusterStatus  OBJECT-TYPE
   SYNTAX      OCTET STRING
   MAX-ACCESS  read-only
   STATUS      current
   DESCRIPTION
       "Indicates if the LB is standalone or in a cluster."
   ::= { blbExtStatsSystem 7 }


blbOperationMode  OBJECT-TYPE
   SYNTAX      OCTET STRING
   MAX-ACCESS  read-only
   STATUS      current
   DESCRIPTION
      "Indicates the operating mode of LB(route-path/bridge mode)."
  ::= { blbExtStatsSystem 8 }

---
--blbExtGslbStatsTable
---
blbExtGslbStatsTable   OBJECT-TYPE
   SYNTAX      OCTET STRING
   MAX-ACCESS  read-only
   STATUS      current
   DESCRIPTION
         "Number of requests per GSLB site. "
   ::= { blbExtStatsGSLB 1 }

--
--
-- blbExtTraps 
--
blbExtTraps OBJECT IDENTIFIER ::= { blbExt 3 }
blbSystemTraps OBJECT IDENTIFIER ::= { blbExtTraps 1 }

blbCPUFanDead NOTIFICATION-TYPE
   STATUS      current
   DESCRIPTION
      "Severity: Alert  
       One of the CPU fans is dead."
   ::= { blbSystemTraps 1 }

blbSysFanDead NOTIFICATION-TYPE
   STATUS      current
   DESCRIPTION   
      "Severity: Alert 
      One of the System fans is dead."
   ::= { blbSystemTraps 2 }

blbCPUTempHigh NOTIFICATION-TYPE
   STATUS      current
   DESCRIPTION
      "Severity: Alert
      CPU temperature is higher than 70C."
   ::= { blbSystemTraps 3 }
 
blbCpuTempCritical NOTIFICATION-TYPE
   STATUS      current
   DESCRIPTION
      "Severity: Alert
      CPU temperature is higher than 80C."
   ::= { blbSystemTraps 4 }

blbFirmwareStorageHigh NOTIFICATION-TYPE
   STATUS      current
   DESCRIPTION
      "Severity: Alert
      Firmware storage exceeds 90%."
   ::= { blbSystemTraps 5 }

blbLogsStorageHigh NOTIFICATION-TYPE
   STATUS      current
   DESCRIPTION
     "Severity: Alert
      Logs storage exceeds 85%."
   ::= { blbSystemTraps 6 }

blbHighAvailabilityStatus NOTIFICATION-TYPE
   STATUS      current
   DESCRIPTION
     "Severity: Information
      High Availability Status Changed."
   ::= { blbSystemTraps 7 }

blbEnergizeUpdateExpire NOTIFICATION-TYPE
   STATUS      current
   DESCRIPTION
     "Severity: Information
      Energize update subscription is about to expire."
   ::= { blbSystemTraps 8 }

blbFirmwareUpdateAvailable NOTIFICATION-TYPE
   STATUS      current
   DESCRIPTION
     "Severity: Information
      New firmware update is available."
   ::= { blbSystemTraps 9 }

blbAttackDefinitionUpdateAvailable  NOTIFICATION-TYPE
   STATUS      current
   DESCRIPTION
     "Severity: Information
      New Attack Definition Update available."
   ::= { blbSystemTraps 10 }

blbNewAttackDefinitionInstalled NOTIFICATION-TYPE
   STATUS      current
   DESCRIPTION
     "Severity: Information
      New Attack Definition is installed."
   ::= { blbSystemTraps 11 }


blbTrafficTraps OBJECT IDENTIFIER ::= { blbExtTraps 2 }

blbServiceUp NOTIFICATION-TYPE
   STATUS      current
   DESCRIPTION
     "Severity: Information
      Service is up."
   ::= { blbTrafficTraps 1 }

blbServiceDown NOTIFICATION-TYPE
   STATUS      current
   DESCRIPTION
     "Severity: Alert
      Service is down."
   ::= { blbTrafficTraps 2 }


blbServerUp NOTIFICATION-TYPE
   STATUS      current
   DESCRIPTION
     "Severity: Information
      Back-end Server is up."
   ::= { blbTrafficTraps 3 }

blbServerDown NOTIFICATION-TYPE
   STATUS      current
   DESCRIPTION
     "Severity: Alert
      Back-end Server is down."
   ::= { blbTrafficTraps 4 }

blbMinServerThresholdReached NOTIFICATION-TYPE
   STATUS      current
   DESCRIPTION
     "Severity: Alert
      Number of functioning Real Servers drops below Minimum Real Servers."
   ::= { blbTrafficTraps 5}

blbMinServerThresholdCrossed NOTIFICATION-TYPE
   STATUS      current
   DESCRIPTION
     "Severity: Alert
      Number of active Real Servers has returned to minimum server threshold."
   ::= { blbTrafficTraps 6}

END
